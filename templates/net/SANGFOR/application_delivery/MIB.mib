-- File Name : SANGFOR-GENERAL-MIB.mib
-- Date      : Wed Feb 15 20:03:00 CST 2012
-- Author    : WebNMS Agent Toolkit C Edition - MibEditor 6



SANGFOR-GENERAL-MIB	DEFINITIONS ::= BEGIN
	IMPORTS
		DisplayString, PhysAddress, snmp, system
			FROM RFC1213-MIB
		TEXTUAL-CONVENTION, DisplayString
			FROM SNMPv2-TC
		OBJECT-TYPE
			FROM RFC-1212
		enterprises
			FROM RFC1155-SMI;

-- TEXTUAL-CONVENTIONS --
	PhysAddress ::= 		OCTET STRING

	DisplayString ::= 		OCTET STRING

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	sangfor	OBJECT IDENTIFIER
		::=  {  enterprises  35047  }

	general	OBJECT IDENTIFIER
		::=  {  sangfor  1  }

	product	OBJECT IDENTIFIER
		::=  {  sangfor  2  }

	sfDeviceDescr	OBJECT-TYPE	
		SYNTAX			OCTET STRING
		ACCESS			read-only
		STATUS			mandatory
		DESCRIPTION		"Device name & model"
		::=  {  general  1  }

	sfSysDate	OBJECT-TYPE	
		SYNTAX			OCTET STRING
		ACCESS			read-only
		STATUS			mandatory
		DESCRIPTION		"System's date"
		::=  {  general  2  }

	sfSysCpuCostRate	OBJECT-TYPE	
		SYNTAX			INTEGER
		ACCESS			read-only
		STATUS			mandatory
		DESCRIPTION		"CPU current cost percentage (Percent)."
		::=  {  general  3  }


	sfDiskTable	OBJECT-TYPE
		SYNTAX		SEQUENCE  OF  SfDiskEntry
		ACCESS		not-accessible
		STATUS		mandatory
		DESCRIPTION	"Disk infomation table"
		::=  { general  5 }

	sfDiskEntry	OBJECT-TYPE
		SYNTAX		SfDiskEntry
		ACCESS		not-accessible
		STATUS		mandatory
		DESCRIPTION	"One disk infomation"
		INDEX		{  diskIndex  }
		::=  { sfDiskTable 1 }

	SfDiskEntry  ::=  SEQUENCE {
		diskIndex  INTEGER,
		sfFilesystemName  DisplayString,
		sfDiskSize  DisplayString,
		sfDiskUsed  DisplayString,
		sfDiskAvail  DisplayString,
		sfDiskUsedPercent  DisplayString,
		sfIntDiskSize INTEGER,
		sfIntDiskUsed INTEGER,
		sfIntDiskAvail INTEGER,
		sfDiskTemp     INTEGER
		}


	diskIndex	OBJECT-TYPE	
		SYNTAX			INTEGER
		ACCESS			not-accessible
		STATUS			mandatory
		DESCRIPTION		"The disk index"
		::=  {  sfDiskEntry  1  }


	sfFilesystemName	OBJECT-TYPE	
		SYNTAX			DisplayString
		ACCESS			read-only
		STATUS			mandatory
		DESCRIPTION		"File system of the disk"
		::=  {  sfDiskEntry  2  }


	sfDiskSize	OBJECT-TYPE	
		SYNTAX			DisplayString
		ACCESS			read-only
		STATUS			mandatory
		DESCRIPTION		"Size of the disk"
		::=  {  sfDiskEntry  3  }


	sfDiskUsed	OBJECT-TYPE	
		SYNTAX			DisplayString
		ACCESS			read-only
		STATUS			mandatory
		DESCRIPTION		"Used size of the disk"
		::=  {  sfDiskEntry  4  }


	sfDiskAvail	OBJECT-TYPE	
		SYNTAX			DisplayString
		ACCESS			read-only
		STATUS			mandatory
		DESCRIPTION		"Available size of the disk"
		::=  {  sfDiskEntry  5  }


	sfDiskUsedPercent	OBJECT-TYPE	
		SYNTAX			DisplayString
		ACCESS			read-only
		STATUS			mandatory
		DESCRIPTION		"Used percent of the disk (Percent)"
		::=  {  sfDiskEntry  6  }
		
	
	sfIntDiskSize	OBJECT-TYPE	
		SYNTAX			INTEGER
		ACCESS			read-only
		STATUS			mandatory
		DESCRIPTION		"Size of the disk (Mebibyte)"
		::=  {  sfDiskEntry  7  }

	sfIntDiskUsed	OBJECT-TYPE	
		SYNTAX			INTEGER
		ACCESS			read-only
		STATUS			mandatory
		DESCRIPTION		"Used size of the disk (Mebibyte)"
		::=  {  sfDiskEntry  8  }

	sfIntDiskAvail	OBJECT-TYPE	
		SYNTAX			INTEGER
		ACCESS			read-only
		STATUS			mandatory
		DESCRIPTION		"Available size of the disk (Mebibyte)"
		::=  {  sfDiskEntry  9  }

	sfDiskTemp	OBJECT-TYPE	
		SYNTAX			INTEGER
		ACCESS			read-only
		STATUS			mandatory
		DESCRIPTION		"Temperature of the disk (Centigrade)"
		::=  {  sfDiskEntry  10  }

	sfDeviceStatus	OBJECT-TYPE	
		SYNTAX			INTEGER  ( 0 .. 1  ) 
		ACCESS			read-only
		STATUS			mandatory
		DESCRIPTION		"0--warning 1--normal"
		::=  {  general  12  }
		
	sfSysMemory 	OBJECT IDENTIFIER
		::=  {  general  13  }


	sfSysFreeMemory	OBJECT-TYPE	
		SYNTAX			OCTET STRING
		ACCESS			read-only
		STATUS			mandatory
		DESCRIPTION		"Free memory (Kibibyte)"
	::=  {  sfSysMemory  1  }

	sfSysTotalMemory	OBJECT-TYPE	
		SYNTAX			OCTET STRING
		ACCESS			read-only
		STATUS			mandatory
		DESCRIPTION		"Total memory (Kibibyte)"
	::=  {  sfSysMemory  2  }

	sfIntSysFreeMemory	OBJECT-TYPE	
		SYNTAX			INTEGER
		ACCESS			read-only
		STATUS			mandatory
		DESCRIPTION		"Free memory (Kibibyte)"
	::=  {  sfSysMemory  3  }

	sfIntSysTotalMemory	OBJECT-TYPE	
		SYNTAX			INTEGER
		ACCESS			read-only
		STATUS			mandatory
		DESCRIPTION		"Total memory (Kibibyte)"
	::=  {  sfSysMemory  4  }
	
	sfSysFanTable	OBJECT-TYPE
		SYNTAX		SEQUENCE  OF  sfSysFanEntry
		ACCESS		not-accessible
		STATUS		mandatory
		DESCRIPTION	"Fan information table"
	::=  { general  14}

	sfSysFanEntry	OBJECT-TYPE
		SYNTAX		sfSysFanEntry
		ACCESS		not-accessible
		STATUS		mandatory
		DESCRIPTION	"One Fan information"
		INDEX		{  fanIndex  }
		::=  { sfSysFanTable 1 }

	sfSysFanEntry  ::=  SEQUENCE {
		fanIndex  INTEGER,
		sfFanName  OCTET STRING,
		sfFanSpeed INTEGER,
		sfFanState  OCTET STRING
	}

	fanIndex	OBJECT-TYPE	
		SYNTAX			INTEGER
		ACCESS			not-accessible
		STATUS			mandatory
		DESCRIPTION		"The Fan index"
	::=  {  sfSysFanEntry  1  }

	sfFanName	OBJECT-TYPE	
		SYNTAX			OCTET STRING
		ACCESS			not-accessible
		STATUS			mandatory
		DESCRIPTION		"The Fan Name"
	::=  {  sfSysFanEntry  2  }

	sfFanSpeed	OBJECT-TYPE	
		SYNTAX			INTEGER
		ACCESS			not-accessible
		STATUS			mandatory
		DESCRIPTION		"The Fan speed (RPM)"
	::=  {  sfSysFanEntry  3  }

	sfFanState	OBJECT-TYPE	
		SYNTAX			OCTET STRING
		ACCESS			not-accessible
		STATUS			mandatory
		DESCRIPTION		"The Fan state:
	                      0 - Warning; 
	                      1 - Normal; 
	                      2 - High;
	                      3 - Very High"
	::=  {  sfSysFanEntry  4 }
	
	sfSysPowerTable	OBJECT-TYPE
		SYNTAX		SEQUENCE  OF  sfSysPowerEntry
		ACCESS		not-accessible
		STATUS		mandatory
		DESCRIPTION	"Power information table"
	::=  { general  15}

	sfSysPowerEntry	OBJECT-TYPE
		SYNTAX		sfSysPowerEntry
		ACCESS		not-accessible
		STATUS		mandatory
		DESCRIPTION	"One Power information"
		INDEX		{  powerIndex  }
		::=  { sfSysPowerTable 1 }

	sfSysPowerEntry  ::=  SEQUENCE {
			powerIndex  INTEGER,
			sfPowerName  OCTET STRING,
			sfPowerState OCTET STRING
	}

	powerIndex	OBJECT-TYPE	
		SYNTAX			INTEGER
		ACCESS			not-accessible
		STATUS			mandatory
		DESCRIPTION		"The Power index"
	::=  {  sfSysPowerEntry  1  }

	sfPowerName	OBJECT-TYPE	
		SYNTAX			OCTET STRING
		ACCESS			not-accessible
		STATUS			mandatory
		DESCRIPTION		"The Power Name"
	::=  {  sfSysPowerEntry  2  }

	sfPowerState	OBJECT-TYPE	
		SYNTAX			OCTET STRING
		ACCESS			not-accessible
		STATUS			mandatory
		DESCRIPTION	"The Power state:
					  1- Unknown 
					  2- Up and running
					  3- Ready to run, not running yet
					  4- Held in reset, not ready yet
			          5- Running at Full Speed (valid for fans only)								
                      6- Down or off (for power supply) 
			          7- Running as a standby (Backup)"
	::=  {  sfSysPowerEntry  3  }

	sfCpuTable	OBJECT-TYPE
		SYNTAX		SEQUENCE  OF  SfCpuEntry
		ACCESS		not-accessible
		STATUS		mandatory
		DESCRIPTION	"CPU information table"
		::=  { general  16 }

	sfCpuEntry	OBJECT-TYPE
		SYNTAX		SfCpuEntry
		ACCESS		not-accessible
		STATUS		mandatory
		DESCRIPTION	"One CPU information"
		INDEX		{  cpuIndex  }
		::=  { sfCpuTable 1 }

	SfCpuEntry  ::=  SEQUENCE {
		cpuIndex  INTEGER,
		sfCpuName  OCTET STRING,
		sfCpuLoadLast1Min  OCTET STRING,
		sfCpuLoadLast5Min  OCTET STRING,
		sfCpuLoadLast15Min  OCTET STRING,
		sfCpuTemp  OCTET STRING,
		sfIntCpuTemp INTEGER
		}


	cpuIndex	OBJECT-TYPE	
		SYNTAX			INTEGER
		ACCESS			not-accessible
		STATUS			mandatory
		DESCRIPTION		"The index of CPU table"
		::=  {  sfCpuEntry  1  }


	sfCpuName	OBJECT-TYPE	
		SYNTAX			OCTET STRING
		ACCESS			read-only
		STATUS			mandatory
		DESCRIPTION		"CPU's name or number"
		::=  {  sfCpuEntry  2  }


	sfCpuLoadLast1Min	OBJECT-TYPE	
		SYNTAX			OCTET STRING
		ACCESS			read-only
		STATUS			mandatory
		DESCRIPTION		"Load average in past 1 minute (Percent)"
		::=  {  sfCpuEntry  3  }


	sfCpuLoadLast5Min	OBJECT-TYPE	
		SYNTAX			OCTET STRING
		ACCESS			read-only
		STATUS			mandatory
		DESCRIPTION		"Load average in past 5 minutes (Percent)"
		::=  {  sfCpuEntry  4  }


	sfCpuLoadLast15Min	OBJECT-TYPE	
		SYNTAX			OCTET STRING
		ACCESS			read-only
		STATUS			mandatory
		DESCRIPTION		"Load average in past 15 minutes (Percent)"
		::=  {  sfCpuEntry  5  }


	sfCpuTemp	OBJECT-TYPE	
		SYNTAX			OCTET STRING
		ACCESS			read-only
		STATUS			mandatory
		DESCRIPTION		"Current temperature ends with 'C' (Centigrade)"
		::=  {  sfCpuEntry  6  }
		
		
	sfIntCpuTemp	OBJECT-TYPE	
		SYNTAX			INTEGER
		ACCESS			read-only
		STATUS			mandatory
		DESCRIPTION		"Current temperature (Centigrade)"
	    ::=  {  sfCpuEntry  7  }

	sfSysDevName	OBJECT-TYPE	
		SYNTAX			OCTET STRING
		ACCESS			read-only
		STATUS			mandatory
		DESCRIPTION		"System Name"
	::=  {  general  17  }

	sfSysSoftVersion	OBJECT-TYPE	
		SYNTAX			OCTET STRING
		ACCESS			read-only
		STATUS			mandatory
		DESCRIPTION		"System software version"
	::=  {  general  18  }
	aC	OBJECT IDENTIFIER
		::=  {  product  1  }

	aD	OBJECT IDENTIFIER
		::=  {  product  2  }

	aPM	OBJECT IDENTIFIER
		::=  {  product  3  }

	aF	OBJECT IDENTIFIER
		::=  {  product  4  }

	bM	OBJECT IDENTIFIER
		::=  {  product  5  }

	iPSecVPN	OBJECT IDENTIFIER
		::=  {  product  6  }

	nAC	OBJECT IDENTIFIER
		::=  {  product  7  }

	sC	OBJECT IDENTIFIER
		::=  {  product  8  }

	sG	OBJECT IDENTIFIER
		::=  {  product  9  }

	sSLVPN	OBJECT IDENTIFIER
		::=  {  product  10  }

	wANACC	OBJECT IDENTIFIER
		::=  {  product  11  }

	pGeneral	OBJECT IDENTIFIER
		::=  {  product  100  }

	sfDhcp	OBJECT IDENTIFIER
		::=  {  pGeneral  1  }

	sfEnableDHCP	OBJECT-TYPE	
		SYNTAX			INTEGER  ( 0 .. 1  ) 
		ACCESS			read-only
		STATUS			mandatory
		DESCRIPTION		"0--disable 1--enable"
	::=  {  sfDhcp  1  }

	sfNumOfTotalIpAddr	OBJECT-TYPE	
		SYNTAX			INTEGER
		ACCESS			read-only
		STATUS			mandatory
		DESCRIPTION		"The total IP address's number in IP pool"
		::=  {  sfDhcp  2  }

	sfNumOfLeftIp	OBJECT-TYPE	
		SYNTAX			INTEGER
		ACCESS			read-only
		STATUS			mandatory
		DESCRIPTION		"The number of left."
		::=  {  sfDhcp  3  }

	sfNumOfOccupyIp	OBJECT-TYPE	
		SYNTAX			INTEGER
		ACCESS			read-only
		STATUS			mandatory
		DESCRIPTION		"The number which already be used"
		::=  {  sfDhcp  4  }
		
	sfEnableDoubleHost	OBJECT-TYPE	
		SYNTAX			INTEGER  ( 0 .. 1  ) 
		ACCESS			read-only
		STATUS			mandatory
		DESCRIPTION		"0--disable 1--enable"
		::=  {  pGeneral  3  }

	adConns	OBJECT-TYPE	
		SYNTAX			INTEGER
		ACCESS			read-only
		STATUS			mandatory
		DESCRIPTION		"Concurrent connections (Bit Per Second)"
		::=  {  aD  1  }

	adNewConns	OBJECT-TYPE	
		SYNTAX			INTEGER
		ACCESS			read-only
		STATUS			mandatory
		DESCRIPTION		"New connections (Connection Per Second)"
		::=  {  aD  2  }

	adVsConns	OBJECT-TYPE	
		SYNTAX			INTEGER
		ACCESS			read-only
		STATUS			mandatory
		DESCRIPTION		"Virtual service connections (Connection)"
		::=  {  aD  3  }

	adVsNewConns	OBJECT-TYPE	
		SYNTAX			INTEGER
		ACCESS			read-only
		STATUS			mandatory
		DESCRIPTION		"New virtual service connections (Connection Per Second)"
		::=  {  aD  4  }

	adUplinkThroughput	OBJECT-TYPE	
		SYNTAX			INTEGER
		ACCESS			read-only
		STATUS			mandatory
		DESCRIPTION		"All wan links' network Uplink Throughput (Bit Per Second)"
		::=  {  aD  5  }

	adDownlinkThroughput	OBJECT-TYPE	
		SYNTAX			INTEGER
		ACCESS			read-only
		STATUS			mandatory
		DESCRIPTION		"All wan links' network Downlink Throughput (Bit Per Second)"
		::=  {  aD  6  }

	adIfTable	OBJECT-TYPE
		SYNTAX		SEQUENCE  OF  AdIfEntry
		ACCESS		not-accessible
		STATUS		mandatory
		DESCRIPTION	"AD interface information"
		::=  { aD  7 }

	adIfEntry	OBJECT-TYPE
		SYNTAX		AdIfEntry
		ACCESS		not-accessible
		STATUS		mandatory
		DESCRIPTION	"AD interface entry"
		INDEX		{  ifIndex  }
		::=  { adIfTable 1 }

	AdIfEntry  ::=  SEQUENCE {
		ifIndex  INTEGER,
		adIfName  OCTET STRING,
		adIfSpeed  OCTET STRING,
		adIfDescription  OCTET STRING
		}


	ifIndex	OBJECT-TYPE	
		SYNTAX			INTEGER
		ACCESS			not-accessible
		STATUS			mandatory
		DESCRIPTION		"The interface index"
		::=  {  adIfEntry  1  }


	adIfName	OBJECT-TYPE	
		SYNTAX			OCTET STRING
		ACCESS			read-only
		STATUS			mandatory
		DESCRIPTION		"Interface name"
		::=  {  adIfEntry  2  }


	adIfSpeed	OBJECT-TYPE	
		SYNTAX			OCTET STRING
		ACCESS			read-only
		STATUS			mandatory
		DESCRIPTION		"Interface speed mode"
		::=  {  adIfEntry  3  }

	adIfDescription	OBJECT-TYPE	
		SYNTAX			OCTET STRING
		ACCESS			read-only
		STATUS			mandatory
		DESCRIPTION		"Description of the interface"
		::=  {  adIfEntry  4  }

	adBondTable	OBJECT-TYPE
		SYNTAX		SEQUENCE  OF  AdBondEntry
		ACCESS		not-accessible
		STATUS		mandatory
		DESCRIPTION	"AD bonds infomation"
		::=  { aD  8 }

	adBondEntry	OBJECT-TYPE
		SYNTAX		AdBondEntry
		ACCESS		not-accessible
		STATUS		mandatory
		DESCRIPTION	"One bond infomation"
		INDEX		{  bondIndex  }
		::=  { adBondTable 1 }

	AdBondEntry  ::=  SEQUENCE {
		bondIndex  INTEGER,
		adBondName  OCTET STRING,
		adBondSlaveIf  OCTET STRING,
		adBondDescription  OCTET STRING
		}


	bondIndex	OBJECT-TYPE	
		SYNTAX			INTEGER
		ACCESS			not-accessible
		STATUS			mandatory
		DESCRIPTION		"The bond index"
		::=  {  adBondEntry  1  }


	adBondName	OBJECT-TYPE	
		SYNTAX			OCTET STRING
		ACCESS			read-only
		STATUS			mandatory
		DESCRIPTION		"The bond name"
		::=  {  adBondEntry  2  }


	adBondSlaveIf	OBJECT-TYPE	
		SYNTAX			OCTET STRING
		ACCESS			read-only
		STATUS			mandatory
		DESCRIPTION		"Slave interfaces of bond"
		::=  {  adBondEntry  3  }

	adBondDescription	OBJECT-TYPE	
		SYNTAX			OCTET STRING
		ACCESS			read-only
		STATUS			mandatory
		DESCRIPTION		"Description of the bond"
		::=  {  adBondEntry  4  }

	adSwitchTable	OBJECT-TYPE
		SYNTAX		SEQUENCE  OF  AdSwitchEntry
		ACCESS		not-accessible
		STATUS		mandatory
		DESCRIPTION	"AD switch information"
		::=  { aD  9 }

	adSwitchEntry	OBJECT-TYPE
		SYNTAX		AdSwitchEntry
		ACCESS		not-accessible
		STATUS		mandatory
		DESCRIPTION	"Switch table entry"
		INDEX		{  switchIndex  }
		::=  { adSwitchTable 1 }

	AdSwitchEntry  ::=  SEQUENCE {
		switchIndex  INTEGER,
		adSwitchName  OCTET STRING,
		adSwitchSlaveIf  OCTET STRING,
		adSwitchDescription  OCTET STRING
		}


	switchIndex	OBJECT-TYPE	
		SYNTAX			INTEGER
		ACCESS			not-accessible
		STATUS			mandatory
		DESCRIPTION		"The index of switch table"
		::=  {  adSwitchEntry  1  }


	adSwitchName	OBJECT-TYPE	
		SYNTAX			OCTET STRING
		ACCESS			read-only
		STATUS			mandatory
		DESCRIPTION		"The switch name"
		::=  {  adSwitchEntry  2  }


	adSwitchSlaveIf	OBJECT-TYPE	
		SYNTAX			OCTET STRING
		ACCESS			read-only
		STATUS			mandatory
		DESCRIPTION		"The interfaces of the switch"
		::=  {  adSwitchEntry  3  }

	adSwitchDescription	OBJECT-TYPE	
		SYNTAX			OCTET STRING
		ACCESS			read-only
		STATUS			mandatory
		DESCRIPTION		"Description of the switch"
		::=  {  adSwitchEntry  4  }


	adSystemWarn	OBJECT-TYPE	
		SYNTAX			OCTET STRING
		ACCESS			read-only
		STATUS			mandatory
		DESCRIPTION		"System warn information,just use for systemWarnTrap"
		::=  {  aD  10  }

	egpNeighborLoss	TRAP-TYPE
		ENTERPRISE		snmp
		VARIABLES		{ egpNeighAddr }
		DESCRIPTION		"egpNeighborLoss trap"
		::=  5
	warmStart	TRAP-TYPE
		ENTERPRISE		snmp
		DESCRIPTION		"WarmStart trap"
		::=  1
	coldStart	TRAP-TYPE
		ENTERPRISE		snmp
		DESCRIPTION		"ColdStart trap"
		::=  0
	linkUp	TRAP-TYPE
		ENTERPRISE		snmp
		VARIABLES		{ ifIndex }
		DESCRIPTION		"LinkUp trap"
		::=  3
	linkDown	TRAP-TYPE
		ENTERPRISE		snmp
		VARIABLES		{ ifIndex }
		DESCRIPTION		"LinkDown trap"
		::=  2
	authenticationFailure	TRAP-TYPE
		ENTERPRISE		snmp
		DESCRIPTION		"AuthenticationFailure trap"
		::=  4
	enterpriseSpecific	TRAP-TYPE
		ENTERPRISE		sangfor
		VARIABLES		{ sfSysIpAddr }
		DESCRIPTION		"EnterpriseSpecific trap"
		::=  6
	systemWarnTrap	TRAP-TYPE
		ENTERPRISE		sangfor
		VARIABLES		{ adSystemWarn }
		DESCRIPTION		"System warn trap"
		::=  7
	
	cpuWarnTrap	TRAP-TYPE
		ENTERPRISE		sangfor
		VARIABLES		{ adCpuTrapInfo }
		DESCRIPTION		"CPU warn trap"
		::=  8
	memWarnTrap	TRAP-TYPE
		ENTERPRISE		sangfor
		VARIABLES		{ adMemTrapInfo }
		DESCRIPTION		"MEM warn trap"
		::=  9
	diskWarnTrap	TRAP-TYPE
		ENTERPRISE		sangfor
		VARIABLES		{ adDiskTrapInfo }
		DESCRIPTION		"Disk warn trap"
		::=  10
	sysConnsWarnTrap	TRAP-TYPE
		ENTERPRISE		sangfor
		VARIABLES		{ adSysConnsTrapInfo }
		DESCRIPTION		"System conns warn trap"
		::=  11
	vsConnsWarnTrap	TRAP-TYPE
		ENTERPRISE		sangfor
		VARIABLES		{ adVsConnsTrapInfo }
		DESCRIPTION		"VS conns warn trap"
		::=  12
	vsStatusWarnTrap	TRAP-TYPE
		ENTERPRISE		sangfor
		VARIABLES		{ adVsStatusTrapInfo }
		DESCRIPTION		"VS status warn trap"
		::=  13
	nodeStatusWarnTrap	TRAP-TYPE
		ENTERPRISE		sangfor
		VARIABLES		{ adNodeStatusTrapInfo }
		DESCRIPTION		"Node status warn trap"
		::=  14
	linkStatusWarnTrap TRAP-TYPE
		ENTERPRISE      sangfor
		VARIABLES       { adLinkStatusTrapInfo }
		DESCRIPTION     "Link status warn trap"
		::=  15
	crlWarnTrap         TRAP-TYPE
		ENTERPRISE      sangfor
		VARIABLES       { adCrlTrapInfo }
		DESCRIPTION     "CRL warn trap"
		::= 16
	attackWarnTrap      TRAP-TYPE
		ENTERPRISE      sangfor
		VARIABLES       { adAttackTrapInfo }
		DESCRIPTION     "Attack warn trap"
		::= 17
	clusterWarnTrap     TRAP-TYPE
		ENTERPRISE      sangfor
		VARIABLES       { adClusterTrapInfo }
		DESCRIPTION     "Cluster warn trap"
		::= 18
	logRegexWarnTrap    TRAP-TYPE
		ENTERPRISE      sangfor
		VARIABLES       { adLogRegexTrapInfo }
		DESCRIPTION     "Log regex warn trap"
		::= 19
		
	crlLoadSuccessTrap TRAP-TYPE
		ENTERPRISE		sangfor
		VARIABLES		{ adCrlLoadTrapInfo }
		DESCRIPTION		"CRL load success trap"
		::=  20

	crlLoadFailTrap TRAP-TYPE
		ENTERPRISE		sangfor
		VARIABLES		{ adCrlLoadTrapInfo }
		DESCRIPTION		"CRL load fail trap"
		::=  21

	powerWarnTrap TRAP-TYPE
		ENTERPRISE		sangfor
		VARIABLES		{ adPowerTrapInfo }
		DESCRIPTION		"Power warn trap"
		::=  22

	interfaceWarnTrap TRAP-TYPE
		ENTERPRISE		sangfor
		VARIABLES		{ adInterfaceTrapInfo }
		DESCRIPTION		"Link interface warn trap"
		::=  23
	
	vsnewConnsWarnTrap	TRAP-TYPE
		ENTERPRISE		sangfor
		VARIABLES		{ adVsnewConnsTrapInfo }
		DESCRIPTION		"virtual service new conns warn trap"
		::=  24
	sysnewConnsWarnTrap	TRAP-TYPE
		ENTERPRISE		sangfor
		VARIABLES		{ adSysnewConnsTrapInfo }
		DESCRIPTION		"system new conns warn trap"
		::=  25	
	wanFluxWarnTrap	TRAP-TYPE
		ENTERPRISE		sangfor
		VARIABLES		{ adWanFluxTrapInfo }
		DESCRIPTION		"wan flux warn trap"
		::=  26

	certificateWarnTrap TRAP-TYPE
		ENTERPRISE		sangfor
		VARIABLES		{ adCertificateTrapInfo }
		DESCRIPTION		"Certificate expired warn trap"
		::=  27

	securityStatusWarnTrap TRAP-TYPE
		ENTERPRISE		sangfor
		VARIABLES		{ adSecurityStatusTrapInfo }
		DESCRIPTION		"security expired warn trap"
		::=  28

	adVsTable	OBJECT-TYPE
		SYNTAX		SEQUENCE  OF  AdVsEntry
		ACCESS		not-accessible
		STATUS		mandatory
		DESCRIPTION	"AD VS infomation"
		::=  { aD  11 }

	adVsEntry	OBJECT-TYPE
		SYNTAX		AdVsEntry
		ACCESS		not-accessible
		STATUS		mandatory
		DESCRIPTION	"One VS infomation"
		INDEX		{  vsIndex  }
		::=  { adVsTable 1 }

	AdVsEntry  ::=  SEQUENCE {
		vsIndex  INTEGER,
		adVsName  OCTET STRING,
		adVsStatus  INTEGER,
		adVsBitIn  Counter64,
		adVsBitOut  Counter64,
		adVsPacketIn  Counter64,
		adVsPacketOut  Counter64,
		adVsConnNew  Counter64,
		adVsConnCur  Counter64,
		adVsConnMax  Counter64,
		adVsConnTotal  Counter64,
		adVsRequestTotal  Counter64,
		adVsRequestNew  Counter64,
		adVsMysqlReadRate INTEGER, 
		adVsMysqlWriteRate INTEGER,
		adVsIP  OCTET STRING,
		adVsHealthStatus  OCTET STRING,
		adVsHealthNodeCnt  	INTEGER,
		adVsPort    OCTET STRING,
		adVsUpThrouthput  Counter64,
		adVsDownThrouthput  Counter64,
		adVsOffloadingSucceedConnNew Counter64,	
		adVsOffloadingSucceedConns Counter64,
		adVsConnCurEst  Counter64,
		adVsDefNodePoolName  OCTET STRING
		}


	vsIndex	OBJECT-TYPE	
		SYNTAX			INTEGER
		ACCESS			not-accessible
		STATUS			mandatory
		DESCRIPTION		"The VS index"
		::=  {  adVsEntry  1  }


	adVsName	OBJECT-TYPE	
		SYNTAX			OCTET STRING
		ACCESS			read-only
		STATUS			mandatory
		DESCRIPTION		"Name of VS"
		::=  {  adVsEntry  2  }


	adVsStatus	OBJECT-TYPE	
		SYNTAX			INTEGER
		ACCESS			read-only
		STATUS			mandatory
		DESCRIPTION		"Status of VS: [0:disable, 1:enable]"
		::=  {  adVsEntry  3  }

	adVsBitIn	OBJECT-TYPE	
		SYNTAX			Counter64
		ACCESS			read-only
		STATUS			mandatory
		DESCRIPTION		"In bits of VS (Bit)"
		::=  {  adVsEntry  4  }

	adVsBitOut	OBJECT-TYPE	
		SYNTAX			Counter64
		ACCESS			read-only
		STATUS			mandatory
		DESCRIPTION		"Out bits of VS (Bit)"
		::=  {  adVsEntry  5  }

	adVsPacketIn	OBJECT-TYPE	
		SYNTAX			Counter64
		ACCESS			read-only
		STATUS			mandatory
		DESCRIPTION		"In packets of VS (Packet)"
		::=  {  adVsEntry  6  }

	adVsPacketOut	OBJECT-TYPE	
		SYNTAX			Counter64
		ACCESS			read-only
		STATUS			mandatory
		DESCRIPTION		"Out packets of VS (Packet)"
		::=  {  adVsEntry  7  }

	adVsConnNew	OBJECT-TYPE	
		SYNTAX			Counter64
		ACCESS			read-only
		STATUS			mandatory
		DESCRIPTION		"New connection of VS (Connection Per Second)"
		::=  {  adVsEntry  8  }

	adVsConnCur	OBJECT-TYPE	
		SYNTAX			Counter64
		ACCESS			read-only
		STATUS			mandatory
		DESCRIPTION		"Current connection of VS (Connection)"
		::=  {  adVsEntry  9  }

	adVsConnMax	OBJECT-TYPE	
		SYNTAX			Counter64
		ACCESS			read-only
		STATUS			mandatory
		DESCRIPTION		"Max connection of VS (Connection)"
		::=  {  adVsEntry  10  }

	adVsConnTotal	OBJECT-TYPE	
		SYNTAX			Counter64
		ACCESS			read-only
		STATUS			mandatory
		DESCRIPTION		"Total connection of VS (Connection)"
		::=  {  adVsEntry  11  }

	adVsRequestTotal	OBJECT-TYPE	
		SYNTAX			Counter64
		ACCESS			read-only
		STATUS			mandatory
		DESCRIPTION		"Total requests of VS (Request)"
		::=  {  adVsEntry  12  }

	adVsRequestNew	OBJECT-TYPE	
		SYNTAX			Counter64
		ACCESS			read-only
		STATUS			mandatory
		DESCRIPTION		"Requests rate of VS (Request Per Second)"
		::=  {  adVsEntry  13  }

	adVsMysqlReadRate	OBJECT-TYPE	
		SYNTAX			INTEGER
		ACCESS			read-only
		STATUS			mandatory
		DESCRIPTION		"MySQL read rate"
		::=  {  adVsEntry  14  }
	
	adVsMysqlWriteRate	OBJECT-TYPE	
		SYNTAX			INTEGER
		ACCESS			read-only
		STATUS			mandatory
		DESCRIPTION		"MySQL write rate"
		::=  {  adVsEntry  15  }
		
	
	adVsIP	OBJECT-TYPE	
		SYNTAX			OCTET STRING
		ACCESS			read-only
		STATUS			mandatory
		DESCRIPTION		"Virtual service IP address"
		::=  {  adVsEntry  16  }

	adVsHealthStatus	OBJECT-TYPE	
		SYNTAX			OCTET STRING
		ACCESS			read-only
		STATUS			mandatory
		DESCRIPTION		"Virtual service health status: [UP, DOWN, ALARM]"
		::=  {  adVsEntry  17  }
		
	adVsHealthNodeCnt	OBJECT-TYPE	
		SYNTAX			INTEGER
		ACCESS			read-only
		STATUS			mandatory
		DESCRIPTION		"Virtual service health nodes count"
		::=  {  adVsEntry  18  }

	adVsPort            OBJECT-TYPE
		SYNTAX          OCTET STRING
		ACCESS          read-only
		STATUS          mandatory
		DESCRIPTION     "Virtual service port list"
		::= { adVsEntry 19 }

	adVsUpThrouthput	OBJECT-TYPE
		SYNTAX			Counter64
		ACCESS			read-only
		STATUS			mandatory
		DESCRIPTION		"Up throughput of VS (Bit Per Second)"
		::=  {  adVsEntry  20  }

	adVsDownThrouthput	OBJECT-TYPE
		SYNTAX			Counter64
		ACCESS			read-only
		STATUS			mandatory
		DESCRIPTION		"Down throughput of VS (Bit Per Second)"
		::=  {  adVsEntry  21  }
	adVsOffloadingSucceedConnNew	OBJECT-TYPE	
		SYNTAX			Counter64
		ACCESS			read-only
		STATUS			mandatory
		DESCRIPTION		"Succeed tps of SSL offloading VS (Transaction Per Second)"
		::=  {  adVsEntry  22  }
	adVsOffloadingSucceedConns 	OBJECT-TYPE	
		SYNTAX			Counter64
		ACCESS			read-only
		STATUS			mandatory
		DESCRIPTION		"Succeed connections of SSL offloading VS (Connection Per Second)"
		::=  {  adVsEntry  23  }
	adVsConnCurEst	OBJECT-TYPE	
		SYNTAX			Counter64
		ACCESS			read-only
		STATUS			mandatory
		DESCRIPTION		"current connection_est of vs"
		::=  {  adVsEntry  24  }
	adVsDefNodePoolName 	OBJECT-TYPE
		SYNTAX			OCTET STRING
		ACCESS			read-only
		STATUS			mandatory
		DESCRIPTION		"Name of default node-pool of VS"
		::=  {  adVsEntry  25  }

	adPoolTable	OBJECT-TYPE
		SYNTAX		SEQUENCE  OF  AdPoolEntry
		ACCESS		not-accessible
		STATUS		mandatory
		DESCRIPTION	"AD pool infomation"
		::=  { aD  12 }

	adPoolEntry	OBJECT-TYPE
		SYNTAX		AdPoolEntry
		ACCESS		not-accessible
		STATUS		mandatory
		DESCRIPTION	"One pool infomation"
		INDEX		{  poolIndex  }
		::=  { adPoolTable 1 }

	AdPoolEntry  ::=  SEQUENCE {
		poolIndex  INTEGER,
		adPoolName  OCTET STRING,
		adPoolConfigStatus  INTEGER,
		adPoolHealthStatus  INTEGER,
		adPoolBitIn  Counter64,
		adPoolBitOut  Counter64,
		adPoolPacketIn  Counter64,
		adPoolPacketOut  Counter64,
		adPoolConnNew  Counter64,
		adPoolConnCur  Counter64,
		adPoolConnMax  Counter64,
		adPoolConnTotal  Counter64,
		adPoolRequestTotal  Counter64,
		adPoolRequestNew  Counter64,
		adPoolMysqlReadRate INTEGER, 
		adPoolMysqlWriteRate INTEGER,
		adPoolConnCurEst  Counter64
		}

	poolIndex	OBJECT-TYPE	
		SYNTAX			INTEGER
		ACCESS			not-accessible
		STATUS			mandatory
		DESCRIPTION		"The pool index"
		::=  {  adPoolEntry  1  }


	adPoolName	OBJECT-TYPE	
		SYNTAX			OCTET STRING
		ACCESS			read-only
		STATUS			mandatory
		DESCRIPTION		"Name of pool"
		::=  {  adPoolEntry  2  }


	adPoolConfigStatus	OBJECT-TYPE	
		SYNTAX			INTEGER
		ACCESS			read-only
		STATUS			mandatory
		DESCRIPTION		"Config status of pool: [0:disable, 1:enable]"
		::=  {  adPoolEntry  3  }

	adPoolHealthStatus	OBJECT-TYPE	
		SYNTAX			INTEGER
		ACCESS			read-only
		STATUS			mandatory
		DESCRIPTION		"Health status of pool: [0:failure, 1:normal, 2:busy, 3:alert]"
		::=  {  adPoolEntry  4  }


	adPoolBitIn	OBJECT-TYPE	
		SYNTAX			Counter64
		ACCESS			read-only
		STATUS			mandatory
		DESCRIPTION		"In bits of pool (Bit)"
		::=  {  adPoolEntry  5  }

	adPoolBitOut	OBJECT-TYPE	
		SYNTAX			Counter64
		ACCESS			read-only
		STATUS			mandatory
		DESCRIPTION		"Out bits of pool (Bit)"
		::=  {  adPoolEntry  6  }

	adPoolPacketIn	OBJECT-TYPE	
		SYNTAX			Counter64
		ACCESS			read-only
		STATUS			mandatory
		DESCRIPTION		"In packets of pool (Packet)"
		::=  {  adPoolEntry  7  }

	adPoolPacketOut	OBJECT-TYPE	
		SYNTAX			Counter64
		ACCESS			read-only
		STATUS			mandatory
		DESCRIPTION		"Out packets of pool (Packet)"
		::=  {  adPoolEntry  8  }

	adPoolConnNew	OBJECT-TYPE	
		SYNTAX			Counter64
		ACCESS			read-only
		STATUS			mandatory
		DESCRIPTION		"New connection of pool (Connection Per Second)"
		::=  {  adPoolEntry  9  }

	adPoolConnCur	OBJECT-TYPE	
		SYNTAX			Counter64
		ACCESS			read-only
		STATUS			mandatory
		DESCRIPTION		"Current connection of pool (Connection)"
		::=  {  adPoolEntry  10  }

	adPoolConnMax	OBJECT-TYPE	
		SYNTAX			Counter64
		ACCESS			read-only
		STATUS			mandatory
		DESCRIPTION		"Max connection of pool (Connection)"
		::=  {  adPoolEntry  11  }

	adPoolConnTotal	OBJECT-TYPE	
		SYNTAX			Counter64
		ACCESS			read-only
		STATUS			mandatory
		DESCRIPTION		"Total connection of pool (Connection)"
		::=  {  adPoolEntry  12  }

	adPoolRequestTotal	OBJECT-TYPE	
		SYNTAX			Counter64
		ACCESS			read-only
		STATUS			mandatory
		DESCRIPTION		"Total requests of pool (Request)"
		::=  {  adPoolEntry  13  }		

	adPoolRequestNew	OBJECT-TYPE	
		SYNTAX			Counter64
		ACCESS			read-only
		STATUS			mandatory
		DESCRIPTION		"Requests of pool (Request Per Second)"
		::=  {  adPoolEntry  14  }
		
	adPoolMysqlReadRate	OBJECT-TYPE	
		SYNTAX			INTEGER
		ACCESS			read-only
		STATUS			mandatory
		DESCRIPTION		"MySQL read rate"
		::=  {  adPoolEntry  15  }
		
	adPoolMysqlWriteRate	OBJECT-TYPE	
		SYNTAX			INTEGER
		ACCESS			read-only
		STATUS			mandatory
		DESCRIPTION		"MySQL write rate"
		::=  {  adPoolEntry  16  }
	
	adPoolConnCurEst	OBJECT-TYPE	
		SYNTAX			Counter64
		ACCESS			read-only
		STATUS			mandatory
		DESCRIPTION		"current connection_est of pool"
		::=  {  adPoolEntry  17  }

	adNodeTable	OBJECT-TYPE
		SYNTAX		SEQUENCE  OF  AdNodeEntry
		ACCESS		not-accessible
		STATUS		mandatory
		DESCRIPTION	"AD node infomation"
		::=  { aD  13 }

	adNodeEntry	OBJECT-TYPE
		SYNTAX		AdNodeEntry
		ACCESS		not-accessible
		STATUS		mandatory
		DESCRIPTION	"One Node infomation"
		INDEX		{  nodeIndex  }
		::=  { adNodeTable 1 }

	AdNodeEntry  ::=  SEQUENCE {
		nodeIndex  INTEGER,
		adNodeName  OCTET STRING,
		adNodeConfigStatus  INTEGER,
		adNodeHealthStatus  INTEGER,
		adNodeBitIn  Counter64,
		adNodeBitOut  Counter64,
		adNodePacketIn  Counter64,
		adNodePacketOut  Counter64,
		adNodeConnNew  Counter64,
		adNodeConnCur  Counter64,
		adNodeConnMax  Counter64,
		adNodeConnTotal  Counter64,
		adNodeRequestTotal  Counter64,
		adNodeRequestNew  Counter64,
		adNodePoolName   OCTET STRING,
		adNodeMysqlReadRate INTEGER, 
		adNodeMysqlWriteRate INTEGER,
		adNodeIP  OCTET STRING,
		adNodePort  INTEGER,
		adNodeConnCurEst  Counter64
		}

	nodeIndex	OBJECT-TYPE	
		SYNTAX			INTEGER
		ACCESS			not-accessible
		STATUS			mandatory
		DESCRIPTION		"The node index"
		::=  {  adNodeEntry  1  }


	adNodeName	OBJECT-TYPE	
		SYNTAX			OCTET STRING
		ACCESS			read-only
		STATUS			mandatory
		DESCRIPTION		"Name of node"
		::=  {  adNodeEntry  2  }


	adNodeConfigStatus	OBJECT-TYPE	
		SYNTAX			INTEGER
		ACCESS			read-only
		STATUS			mandatory
		DESCRIPTION		"Config status of node: [0:disable, 1:enable, 2:offline]"
		::=  {  adNodeEntry  3  }


	adNodeHealthStatus	OBJECT-TYPE	
		SYNTAX			INTEGER
		ACCESS			read-only
		STATUS			mandatory
		DESCRIPTION		"Health status of node: [0:failure, 1:normal, 2:busy]"
		::=  {  adNodeEntry  4  }

	adNodeBitIn	OBJECT-TYPE	
		SYNTAX			Counter64
		ACCESS			read-only
		STATUS			mandatory
		DESCRIPTION		"In bits of node (Bit)"
		::=  {  adNodeEntry  5  }

	adNodeBitOut	OBJECT-TYPE	
		SYNTAX			Counter64
		ACCESS			read-only
		STATUS			mandatory
		DESCRIPTION		"Out bits of node (Bit)"
		::=  {  adNodeEntry  6  }

	adNodePacketIn	OBJECT-TYPE	
		SYNTAX			Counter64
		ACCESS			read-only
		STATUS			mandatory
		DESCRIPTION		"In packets of node (Packet)"
		::=  {  adNodeEntry  7  }

	adNodePacketOut	OBJECT-TYPE	
		SYNTAX			Counter64
		ACCESS			read-only
		STATUS			mandatory
		DESCRIPTION		"Out packets of node ({Packet})"
		::=  {  adNodeEntry  8  }

	adNodeConnNew	OBJECT-TYPE	
		SYNTAX			Counter64
		ACCESS			read-only
		STATUS			mandatory
		DESCRIPTION		"New connection of node (Request Per Second)"
		::=  {  adNodeEntry  9  }

	adNodeConnCur	OBJECT-TYPE	
		SYNTAX			Counter64
		ACCESS			read-only
		STATUS			mandatory
		DESCRIPTION		"Current connection of node (Connection)"
		::=  {  adNodeEntry  10  }

	adNodeConnMax	OBJECT-TYPE	
		SYNTAX			Counter64
		ACCESS			read-only
		STATUS			mandatory
		DESCRIPTION		"Max connection of node (Connection)"
		::=  {  adNodeEntry  11  }

	adNodeConnTotal	OBJECT-TYPE	
		SYNTAX			Counter64
		ACCESS			read-only
		STATUS			mandatory
		DESCRIPTION		"Total connection of node (Connection)"
		::=  {  adNodeEntry  12  }

	adNodeRequestTotal	OBJECT-TYPE	
		SYNTAX			Counter64
		ACCESS			read-only
		STATUS			mandatory
		DESCRIPTION		"Total requests of node (Request)"
		::=  {  adNodeEntry  13  }	

	adNodeRequestNew	OBJECT-TYPE	
		SYNTAX			Counter64
		ACCESS			read-only
		STATUS			mandatory
		DESCRIPTION		"Requests rate of node (Request Per Second)"
		::=  {  adNodeEntry  14  }
		
    adNodePoolName	OBJECT-TYPE	
		SYNTAX			OCTET STRING
		ACCESS			read-only
		STATUS			mandatory
		DESCRIPTION		"Pool name of node"
		::=  {  adNodeEntry  15  }
        
	adNodeMysqlReadRate     OBJECT-TYPE
		SYNTAX			INTEGER
		ACCESS			read-only
		STATUS			mandatory
		DESCRIPTION		"Mysql read rate"
		::=  {  adNodeEntry  16  }

	adNodeMysqlWriteRate     OBJECT-TYPE
		SYNTAX			INTEGER
		ACCESS			read-only
		STATUS			mandatory
		DESCRIPTION		"Mysql write rate"
		::=  {  adNodeEntry  17  }
        
	adNodeIP	OBJECT-TYPE	
		SYNTAX			OCTET STRING
		ACCESS			read-only
		STATUS			mandatory
		DESCRIPTION		"IP of node"
		::=  {  adNodeEntry  18  }
        
	adNodePort	OBJECT-TYPE	
		SYNTAX			INTEGER
		ACCESS			read-only
		STATUS			mandatory
		DESCRIPTION		"Port of node"
		::=  {  adNodeEntry  19  }

	adNodeConnCurEst	OBJECT-TYPE	
		SYNTAX			Counter64
		ACCESS			read-only
		STATUS			mandatory
		DESCRIPTION		"current connection_est of node"
		::=  {  adNodeEntry  20  }
		
	adSnTable	OBJECT-TYPE
		SYNTAX		SEQUENCE  OF  AdSnEntry
		ACCESS		not-accessible
		STATUS		mandatory
		DESCRIPTION	"AD device SN"
		::=  { aD  14 }

	adSnEntry	OBJECT-TYPE
		SYNTAX		AdSnEntry
		ACCESS		not-accessible
		STATUS		mandatory
		DESCRIPTION	"One SN infomation"
		INDEX		{  snIndex  }
		::=  { adSnTable 1 }

	AdSnEntry  ::=  SEQUENCE {
		snIndex  INTEGER,
		adSnName  OCTET STRING,
		adSn  OCTET STRING
		}


	snIndex	OBJECT-TYPE	
		SYNTAX			INTEGER
		ACCESS			not-accessible
		STATUS			mandatory
		DESCRIPTION		"The sn index"
		::=  {  adSnEntry  1  }


	adSnName	OBJECT-TYPE	
		SYNTAX			OCTET STRING
		ACCESS			read-only
		STATUS			mandatory
		DESCRIPTION		"Name of SN"
		::=  {  adSnEntry  2  }

	adSn	OBJECT-TYPE	
		SYNTAX			OCTET STRING
		ACCESS			read-only
		STATUS			mandatory
		DESCRIPTION		"Value of SN"
		::=  {  adSnEntry  3  }
		
	adCpuTable	OBJECT-TYPE
		SYNTAX		SEQUENCE  OF  AdCpuEntry
		ACCESS		not-accessible
		STATUS		mandatory
		DESCRIPTION	"AD CPU Usage"
		::=  { aD  15 }

	adCpuEntry	OBJECT-TYPE
		SYNTAX		AdCpuEntry
		ACCESS		not-accessible
		STATUS		mandatory
		DESCRIPTION	"One core cost rate infomation"
		INDEX		{  adCpuIndex  }
		::=  { adCpuTable 1 }

	AdCpuEntry  ::=  SEQUENCE {
		adCpuIndex  INTEGER,
		adCpuId  INTEGER,
		adCpuUsr  INTEGER,
		adCpuNice  INTEGER,
		adCpuSys  INTEGER,
		adCpuIowait  INTEGER,
		adCpuIrq  INTEGER,
		adCpuSoft  INTEGER,
		adCpuSteal  INTEGER,
		adCpuGuest  INTEGER,
		adCpuIdle  INTEGER,
		adCpuAll  INTEGER,
		adCpuTemp INTEGER
		}


	adCpuIndex	OBJECT-TYPE	
		SYNTAX			INTEGER
		ACCESS			not-accessible
		STATUS			mandatory
		DESCRIPTION		"The core index"
		::=  {  adCpuEntry  1  }


	adCpuId	OBJECT-TYPE	
		SYNTAX			INTEGER
		ACCESS			read-only
		STATUS			mandatory
		DESCRIPTION		"Id of core"
		::=  {  adCpuEntry  2  }

	adCpuUsr	OBJECT-TYPE	
		SYNTAX			INTEGER
		ACCESS			read-only
		STATUS			mandatory
		DESCRIPTION		"CPU time spent in user space of core (Percent)"
		::=  {  adCpuEntry  3  }

	adCpuNice	OBJECT-TYPE	
		SYNTAX			INTEGER
		ACCESS			read-only
		STATUS			mandatory
		DESCRIPTION		"CPU time spent on low priority processes of core (Percent)"
		::=  {  adCpuEntry  4  }

	adCpuSys	OBJECT-TYPE	
		SYNTAX			INTEGER
		ACCESS			read-only
		STATUS			mandatory
		DESCRIPTION		"CPU time spent in kernel space of core (Percent)"
		::=  {  adCpuEntry  5  }

	adCpuIowait	OBJECT-TYPE	
		SYNTAX			INTEGER
		ACCESS			read-only
		STATUS			mandatory
		DESCRIPTION		"CPU time spent in wait of core (Percent)"
		::=  {  adCpuEntry  6  }

	adCpuIrq	OBJECT-TYPE	
		SYNTAX			INTEGER
		ACCESS			read-only
		STATUS			mandatory
		DESCRIPTION		"CPU time spent servicing/handling hardware interrupts of core (Percent)"
		::=  {  adCpuEntry  7  }

	adCpuSoft	OBJECT-TYPE	
		SYNTAX			INTEGER
		ACCESS			read-only
		STATUS			mandatory
		DESCRIPTION		"CPU time spent servicing/handling software interrupts of core (Percent)"
		::=  {  adCpuEntry  8  }

	adCpuSteal	OBJECT-TYPE	
		SYNTAX			INTEGER
		ACCESS			read-only
		STATUS			mandatory
		DESCRIPTION		"CPU time in involuntary wait by virtual cpu while hypervisor is servicing another processor (or) % CPU time stolen from a virtual machine of core (Percent)"
		::=  {  adCpuEntry  9  }

	adCpuGuest	OBJECT-TYPE	
		SYNTAX			INTEGER
		ACCESS			read-only
		STATUS			mandatory
		DESCRIPTION		"CPU time spent to run a virtual processor of core (Percent)"
		::=  {  adCpuEntry  10  }

	adCpuIdle	OBJECT-TYPE	
		SYNTAX			INTEGER
		ACCESS			read-only
		STATUS			mandatory
		DESCRIPTION		"CPU time spent idle of core (Percent)"
		::=  {  adCpuEntry  11  }

	adCpuAll	OBJECT-TYPE	
		SYNTAX			INTEGER
		ACCESS			read-only
		STATUS			mandatory
		DESCRIPTION		"All CPU usage of core (Percent)"
		::=  {  adCpuEntry  12  }

	adCpuTemp   OBJECT-TYPE
		SYNTAX          INTEGER
		ACCESS          read-only
		STATUS          mandatory
		DESCRIPTION     "Ttemperature of core (Centigrade)"
		::=  {  adCpuEntry 13 }

		
	adCpuNum	OBJECT-TYPE	
		SYNTAX			INTEGER
		ACCESS			read-only
		STATUS			mandatory
		DESCRIPTION		"Numbers of CPU"
		::=  {  aD  16  }

	adCoresPerCpu	OBJECT-TYPE	
		SYNTAX			INTEGER
		ACCESS			read-only
		STATUS			mandatory
		DESCRIPTION		"Core numbers of per CPU"
		::=  {  aD  17  }
		
	adClusterStatus	OBJECT-TYPE	
		SYNTAX			INTEGER
		ACCESS			read-only
		STATUS			mandatory
		DESCRIPTION		"Status of cluster (Percent)"
		::=  {  aD  18  }
		
    adMemCostRate	OBJECT-TYPE	
		SYNTAX			INTEGER
		ACCESS			read-only
		STATUS			mandatory
		DESCRIPTION		"Memory usage (Percent)"
		::=  {  aD  19  }

	adCpuCostRate	OBJECT-TYPE	
		SYNTAX			INTEGER
		ACCESS			read-only
		STATUS			mandatory
		DESCRIPTION		"CPU usage (Percent)"
		::=  {  aD  20  }
		
	adHttpRequest	OBJECT-TYPE	
		SYNTAX			INTEGER
		ACCESS			read-only
		STATUS			mandatory
		DESCRIPTION		"HTTP requests (Request)"
		::=  {  aD  21  }			
	adVsNumber	OBJECT-TYPE	
		SYNTAX			INTEGER
		ACCESS			read-only
		STATUS			mandatory
		DESCRIPTION		"VS number"
		::=  {  aD  22  }		
	adPoolNumber	OBJECT-TYPE	
		SYNTAX			INTEGER
		ACCESS			read-only
		STATUS			mandatory
		DESCRIPTION		"Pool number"
		::=  {  aD  23  }		
	adNodeNumber	OBJECT-TYPE	
		SYNTAX			INTEGER
		ACCESS			read-only
		STATUS			mandatory
		DESCRIPTION		"Node number"
		::=  {  aD  24  }
	adEquipType	OBJECT-TYPE	
		SYNTAX			OCTET STRING
		ACCESS			read-write
		STATUS			mandatory
		DESCRIPTION		"ad equipment type"
		::=  {  aD  26  }
	adAppVersion	OBJECT-TYPE	
		SYNTAX			OCTET STRING
		ACCESS			read-only
		STATUS			mandatory
		DESCRIPTION		"ad version"
		::=  {  aD  27  }																	

	adSysName	OBJECT-TYPE	
		SYNTAX			OCTET STRING
		ACCESS			read-write
		STATUS			mandatory
		DESCRIPTION		"System name"
		::=  {  aD  31  }
	adDiskCostRate	OBJECT-TYPE	
		SYNTAX			INTEGER
		ACCESS			read-only
		STATUS			mandatory
		DESCRIPTION		"Disk usage (Percent)"
		::=  {  aD  32  }
		
	
	adCpuThreshold	OBJECT-TYPE	
		SYNTAX		        INTEGER
		ACCESS			read-only
		STATUS			mandatory
		DESCRIPTION		"CPU snmp trap threshold value (Percent)"
		::=  {  aD  33  }
	adMemThreshold	OBJECT-TYPE	
		SYNTAX			INTEGER
		ACCESS			read-only
		STATUS			mandatory
		DESCRIPTION		"MEM snmp trap threshold value (Percent)"
		::=  {  aD  34  }
	adDiskThreshold	OBJECT-TYPE	
		SYNTAX			INTEGER
		ACCESS			read-only
		STATUS			mandatory
		DESCRIPTION		"Disk snmp trap threshold value (Percent)"
		::=  {  aD  35  }
	adConnsThreshold	OBJECT-TYPE	
		SYNTAX			INTEGER
		ACCESS			read-only
		STATUS			mandatory
		DESCRIPTION		"System conns snmp trap threshold value (Cpnnection)"
		::=  {  aD  36  }
	adVsConnsThreshold	OBJECT-TYPE	
		SYNTAX			INTEGER
		ACCESS			read-only
		STATUS			mandatory
		DESCRIPTION		"VS conns snmp trap threshold value (Connection)"
		::=  {  aD  37  }
		
	adCrlTable	OBJECT-TYPE
		SYNTAX		SEQUENCE  OF  SslCrlEntry
		ACCESS		not-accessible
		STATUS		mandatory
		DESCRIPTION	"AD CRL infomation"
		::=  { aD  38 }

	adCrlEntry	OBJECT-TYPE
		SYNTAX		SslCrlEntry
		ACCESS		not-accessible
		STATUS		mandatory
		DESCRIPTION	"CRL table infomation"
		INDEX		{  CrlIndex  }
		::=  { adCrlTable 1 }

	SslCrlEntry  ::=  SEQUENCE {
		CrlIndex  INTEGER,
		adCrlPath  OCTET STRING,
		adCrlDownloadTime OCTET STRING,
		adCrlDownloadStatus OCTET STRING,
		adCrlDownloadCnt OCTET STRING,
		adCrlLoadStartTime	OCTET STRING,
		adCrlLoadEndTime	OCTET STRING,
		adCrlLoadCnt	OCTET STRING,
		adCrlLoadConfName	OCTET STRING
		}

	CrlIndex	OBJECT-TYPE	
		SYNTAX			INTEGER
		ACCESS			not-accessible
		STATUS			mandatory
		DESCRIPTION		"The CRL index"
		::=  {  adCrlEntry  1  }


	adCrlPath	OBJECT-TYPE	
		SYNTAX			OCTET STRING
		ACCESS			read-only
		STATUS			mandatory
		DESCRIPTION		"CRL download path"
		::=  {  adCrlEntry  2  }

	adCrlDownloadTime	OBJECT-TYPE	
		SYNTAX			OCTET STRING
		ACCESS			read-only
		STATUS			mandatory
		DESCRIPTION		"CRL download time"
		::=  {  adCrlEntry  3  }
	
	adCrlDownloadStatus	OBJECT-TYPE	
		SYNTAX			OCTET STRING
		ACCESS			read-only
		STATUS			mandatory
		DESCRIPTION		"CRL download status"
		::=  {  adCrlEntry  4  }

	adCrlDownloadCnt	OBJECT-TYPE	
		SYNTAX			OCTET STRING
		ACCESS			read-only
		STATUS			mandatory
		DESCRIPTION		"CRL download file num"
		::=  {  adCrlEntry  5  }

	adCrlLoadStartTime	OBJECT-TYPE	
		SYNTAX			OCTET STRING
		ACCESS			read-only
		STATUS			mandatory
		DESCRIPTION		"CRL load start time"
		::=  {  adCrlEntry  6  }

	adCrlLoadEndTime	OBJECT-TYPE	
		SYNTAX			OCTET STRING
		ACCESS			read-only
		STATUS			mandatory
		DESCRIPTION		"CRL load end time"
		::=  {  adCrlEntry  7  }

	adCrlLoadCnt	OBJECT-TYPE	
		SYNTAX			OCTET STRING
		ACCESS			read-only
		STATUS			mandatory
		DESCRIPTION		"CRL load count"
		::=  {  adCrlEntry  8  }

	adCrlLoadConfName	OBJECT-TYPE	
		SYNTAX			OCTET STRING
		ACCESS			read-only
		STATUS			mandatory
		DESCRIPTION		"CRL load config name"
		::=  {  adCrlEntry  9  }


	adCrlNumber	OBJECT-TYPE	
		SYNTAX			INTEGER
		ACCESS			read-only
		STATUS			mandatory
		DESCRIPTION		"CRL number"
		::=  {  aD  39  }
		
	adVersion	OBJECT-TYPE	
		SYNTAX			OCTET STRING
		ACCESS			read-only
		STATUS			mandatory
		DESCRIPTION		"Software version"
		::=  {  aD  40  }
		
		
	adLinkTable OBJECT-TYPE
		SYNTAX		SEQUENCE  OF  AdLinkEntry
		ACCESS		not-accessible
		STATUS		mandatory
		DESCRIPTION "AD link infomation"
		::=  { aD 41 }
	
	adLinkEntry OBJECT-TYPE
		SYNTAX 		AdLinkEntry
		ACCESS		not-accessible
		STATUS		mandatory
		DESCRIPTION "One link infomation"
		INDEX		{ LinkIndex  }
		::=	 { adLinkTable 1 }

	AdLinkEntry	 ::= SEQUENCE {
		LinkIndex 	INTEGER,
		adLinkName	OCTET STRING,
		adLinkType	OCTET STRING,
		adLinkIfName OCTET STRING,
		adLinkStatus  INTEGER,
		adLinkBitIn		Counter64,
		adLinkBitOut	Counter64,
		adLinkDescription OCTET STRING
	}

	LinkIndex	OBJECT-TYPE	
		SYNTAX			INTEGER
		ACCESS			not-accessible
		STATUS			mandatory
		DESCRIPTION		"The link index"
		::=  {  adLinkEntry  1  }


	adLinkName	OBJECT-TYPE	
		SYNTAX			OCTET STRING
		ACCESS			read-only
		STATUS			mandatory
		DESCRIPTION		"Name of link"
		::=  {  adLinkEntry  2  }


	adLinkType	OBJECT-TYPE
		SYNTAX			OCTET STRING
		ACCESS			read-only
		STATUS			mandatory
		DESCRIPTION		"Type of link"
		::=  {	adLinkEntry 3  }
	
	adLinkIfName	OBJECT-TYPE	
		SYNTAX			OCTET STRING
		ACCESS			read-only
		STATUS			mandatory
		DESCRIPTION		"Ifname of link"
		::=  {  adLinkEntry  4  }

	adLinkStatus	OBJECT-TYPE	
		SYNTAX			INTEGER
		ACCESS			read-only
		STATUS			mandatory
		DESCRIPTION		"Status of link:[0:failure, 1:normal, 2:busy]"
		::=  {  adLinkEntry  5  }

	adLinkBitIn		OBJECT-TYPE	
		SYNTAX			Counter64
		ACCESS			read-only
		STATUS			mandatory
		DESCRIPTION		"In bits of link (Bit)"
		::=  {  adLinkEntry  6  }


	adLinkBitOut	OBJECT-TYPE	
		SYNTAX			Counter64
		ACCESS			read-only
		STATUS			mandatory
		DESCRIPTION		"Out bits of link (Bit)"
		::=  {  adLinkEntry  7  }

	adLinkDescription	OBJECT-TYPE	
		SYNTAX			OCTET STRING
		ACCESS			read-only
		STATUS			mandatory
		DESCRIPTION		"Description of the link"
		::=  {  adLinkEntry  8  }
		
	adLinkNumber	OBJECT-TYPE	
		SYNTAX			INTEGER
		ACCESS			read-only
		STATUS			mandatory
		DESCRIPTION		"Link number"
		::=  {  aD  42  }
		
	adInterfaceTable OBJECT-TYPE
		SYNTAX		SEQUENCE  OF  AdInterfaceEntry
		ACCESS		not-accessible
		STATUS		mandatory
		DESCRIPTION "AD Interface infomation"
		::=  { aD 43 }
	
	adInterfaceEntry OBJECT-TYPE
		SYNTAX 		AdInterfaceEntry
		ACCESS		not-accessible
		STATUS		mandatory
		DESCRIPTION "One interface infomation"
		INDEX		{ InterfaceIndex  }
		::=	 { adInterfaceTable 1 }

	AdInterfaceEntry	 ::= SEQUENCE {
		InterfaceIndex			INTEGER,
		adInterfaceName			OCTET STRING,
		adInterfaceBitIn		Counter64,
		adInterfaceBitOut		Counter64,
		adInterfacePacketIn		Counter64,
		adInterfacePacketOut	Counter64,
		adInterfaceErrorIn		Counter64,
		adInterfaceErrorOut		Counter64,
		adInterfaceDropIn		Counter64,
		adInterfaceDropOut		Counter64
	}

	InterfaceIndex	OBJECT-TYPE	
		SYNTAX			INTEGER
		ACCESS			not-accessible
		STATUS			mandatory
		DESCRIPTION		"The interface index"
		::=  {  adInterfaceEntry  1  }


	adInterfaceName	OBJECT-TYPE	
		SYNTAX			OCTET STRING
		ACCESS			read-only
		STATUS			mandatory
		DESCRIPTION		"Name of interface"
		::=  {  adInterfaceEntry  2  }


	adInterfaceBitIn	OBJECT-TYPE
		SYNTAX			Counter64
		ACCESS			read-only
		STATUS			mandatory
		DESCRIPTION		"In bits of interface (Bit)"
		::=  {	adInterfaceEntry 3  }
	
	adInterfaceBitOut	OBJECT-TYPE	
		SYNTAX			Counter64
		ACCESS			read-only
		STATUS			mandatory
		DESCRIPTION		"Out bits of interface (Bit)"
		::=  {  adInterfaceEntry  4  }

	adInterfacePacketIn	OBJECT-TYPE	
		SYNTAX			Counter64
		ACCESS			read-only
		STATUS			mandatory
		DESCRIPTION		"In packets of interface (Packet)"
		::=  {  adInterfaceEntry  5  }

	adInterfacePacketOut		OBJECT-TYPE	
		SYNTAX			Counter64
		ACCESS			read-only
		STATUS			mandatory
		DESCRIPTION		"Out packets of interface (Packet)"
		::=  {  adInterfaceEntry  6  }


	adInterfaceErrorIn	OBJECT-TYPE	
		SYNTAX			Counter64
		ACCESS			read-only
		STATUS			mandatory
		DESCRIPTION		"Downlink error packets of interface (Packet)"
		::=  {  adInterfaceEntry  7  }
    
	adInterfaceErrorOut	OBJECT-TYPE	
		SYNTAX			Counter64
		ACCESS			read-only
		STATUS			mandatory
		DESCRIPTION		"Uplink error packets of interface (Packet)"
		::=  {  adInterfaceEntry  8  }
	
	adInterfaceDropIn	OBJECT-TYPE	
		SYNTAX			Counter64
		ACCESS			read-only
		STATUS			mandatory
		DESCRIPTION		"Downlink dropped packets of interfaceol (Packet)"
		::=  {  adInterfaceEntry  9  }
	
	adInterfaceDropOut	OBJECT-TYPE	
		SYNTAX			Counter64
		ACCESS			read-only
		STATUS			mandatory
		DESCRIPTION		"Uplink dropped packets of interface (Packet)"
		::=  {  adInterfaceEntry  10  }
		
	adInterfaceNumber	OBJECT-TYPE	
		SYNTAX			INTEGER
		ACCESS			read-only
		STATUS			mandatory
		DESCRIPTION		"Interface number"
		::=  {  aD  44  }
        
    adSnmpStatus        OBJECT-TYPE
        SYNTAX          INTEGER
        ACCESS          read-only
        STATUS          mandatory
        DESCRIPTION     "0--failed 1--ok"
        ::=  {  aD  45  }
        
    adUptime            OBJECT-TYPE
        SYNTAX          INTEGER
        ACCESS          read-only
        STATUS          mandatory
        DESCRIPTION     "Uptime of device"
        ::=  {  aD  46  }
	
	
	adDevicePattern    OBJECT-TYPE
        SYNTAX          INTEGER
        ACCESS          read-only
        STATUS          mandatory
        DESCRIPTION     "0--master-slave 1--cluster 2--high performance cluster 3--stand-alone"
        ::=  {  aD  47  }
    
    adClusterManageNAME   OBJECT-TYPE
        SYNTAX          OCTET STRING
        ACCESS          read-only
        STATUS          mandatory
        DESCRIPTION     "Name of cluster"
        ::=  {  aD  48  }
        
    adClusterManageIp   OBJECT-TYPE
        SYNTAX          OCTET STRING
        ACCESS          read-only
        STATUS          mandatory
        DESCRIPTION     "Manage IP of cluster"
        ::=  {  aD  49  }
        
    adClusterDevNum     OBJECT-TYPE
        SYNTAX          INTEGER
        ACCESS          read-only
        STATUS          mandatory
        DESCRIPTION     "Number of cluster's devices"
        ::=  {  aD  50  }
        
    adClusterAppGrpNum  OBJECT-TYPE
        SYNTAX          INTEGER
        ACCESS          read-only
        STATUS          mandatory
        DESCRIPTION     "Number of cluster's app groups"
        ::=  {  aD  51  }
        
    adClusterConfVersion    OBJECT-TYPE
        SYNTAX              INTEGER
        ACCESS              read-only
        STATUS              mandatory
        DESCRIPTION        "Config version of the current device"
        ::=  {  aD  52  }
        
    adClusterLocalDevName   OBJECT-TYPE
        SYNTAX              OCTET STRING
        ACCESS              read-only
        STATUS              mandatory
        DESCRIPTION         "Name of the current device"
        ::=  {  aD  53  }
        
    adClusterDevTable   OBJECT-TYPE
        SYNTAX          SEQUENCE OF AdClusterDevEntry
        ACCESS          not-accessible
        STATUS          mandatory
        DESCRIPTION     "Information of cluster's devices"
        ::=  {  aD  54 }
    
    adClusterDevEntry   OBJECT-TYPE
        SYNTAX          AdClusterDevEntry
        ACCESS          not-accessible
        STATUS          mandatory
        DESCRIPTION     "One infomation of cluster's devices"
        INDEX           { ClusterDevIndex }
        ::= { adClusterDevTable 1 }
        
    AdClusterDevEntry   ::= SEQUENCE {
        ClusterDevIndex             INTEGER,
        adClusterDevName            OCTET STRING,
        adClusterDevRole            INTEGER,
        adClusterDevHealthStatus    INTEGER,
        adClusterDevHealthReason    OCTET STRING,
        adClusterDevHAIp            OCTET STRING,
        adClusterDevManageIp        OCTET STRING,
        adClusterDevBackupHAIp      OCTET STRING
    }

	ClusterDevIndex     OBJECT-TYPE
        SYNTAX          INTEGER
        ACCESS          not-accessible
        STATUS          mandatory
        DESCRIPTION     "The cluster device index"
        ::=  { adClusterDevEntry 1 }
    
    adClusterDevName    OBJECT-TYPE
        SYNTAX          OCTET STRING
        ACCESS          read-only
        STATUS          mandatory
        DESCRIPTION     "Name of cluster's device"
        ::= { adClusterDevEntry 2 }
        
    adClusterDevRole    OBJECT-TYPE
        SYNTAX          INTEGER
        ACCESS          read-only
        STATUS          mandatory
        DESCRIPTION     "0--master 1--back_up 2--other"
        ::= { adClusterDevEntry 3}
        
    adClusterDevHealthStatus    OBJECT-TYPE
        SYNTAX                  INTEGER
        ACCESS                  read-only
        STATUS                  mandatory
        DESCRIPTION             "0--init 1--online 2--warning 3--network failure 4--device failure 5--device silenced 6--offline"
        ::= { adClusterDevEntry 4 }
        
    adClusterDevHealthReason    OBJECT-TYPE
        SYNTAX                  OCTET STRING
        ACCESS                  read-only
        STATUS                  mandatory
        DESCRIPTION             "Device health reason"
        ::= { adClusterDevEntry 5 }
        
    adClusterDevHAIp            OBJECT-TYPE
        SYNTAX                  OCTET STRING
        ACCESS                  read-only
        STATUS                  mandatory
        DESCRIPTION             "HA IP/mask of the device"
        ::= { adClusterDevEntry 6 }
        
    adClusterDevManageIp        OBJECT-TYPE
        SYNTAX                  OCTET STRING
        ACCESS                  read-only
        STATUS                  mandatory
        DESCRIPTION             "Manage IP/mask of the device"
        ::= { adClusterDevEntry 7 }
    
    adClusterDevBackupHAIp      OBJECT-TYPE
        SYNTAX                  OCTET STRING
        ACCESS                  read-only
        STATUS                  mandatory
        DESCRIPTION             "backup HA IP/mask of the device"
        ::= { adClusterDevEntry 8 }
        
    adClusterAppTable           OBJECT-TYPE
        SYNTAX                  SEQUENCE OF AdClusterAppEntry
        ACCESS                  not-accessible
        STATUS                  mandatory
        DESCRIPTION             "Infomation of cluster's app groups"
        ::= { aD 55 }
        
    adClusterAppEntry           OBJECT-TYPE
        SYNTAX                  AdClusterAppEntry
        ACCESS                  not-accessible
        STATUS                  mandatory
        DESCRIPTION             "Ine information of cluster's app groups"
        INDEX                   { ClusterAppIndex }
        ::= { adClusterAppTable 1 }
        
    
    AdClusterAppEntry   ::= SEQUENCE {
        ClusterAppIndex             INTEGER,
        adClusterAppName            OCTET STRING,
        adClusterAppActiveDev       OCTET STRING,
        adClusterAppStandByDev      OCTET STRING,
        adClusterAppSyncState       INTEGER
    }
        
    ClusterAppIndex             OBJECT-TYPE
        SYNTAX                  INTEGER
        ACCESS                  not-accessible
        STATUS                  mandatory
        DESCRIPTION             "The cluster app group index"
        ::= { adClusterAppEntry 1 }
        
    adClusterAppName            OBJECT-TYPE
        SYNTAX                  OCTET STRING
        ACCESS                  read-only
        STATUS                  mandatory
        DESCRIPTION             "Name of cluster's app group"
        ::= { adClusterAppEntry 2 }
        
    adClusterAppActiveDev       OBJECT-TYPE
        SYNTAX                  OCTET STRING
        ACCESS                  read-only
        STATUS                  mandatory
        DESCRIPTION             "Active device of the app group"
        ::= { adClusterAppEntry 3 }
        
    adClusterAppStandByDev      OBJECT-TYPE
        SYNTAX                  OCTET STRING
        ACCESS                  read-only
        STATUS                  mandatory
        DESCRIPTION             "Stand by device of the app group"
        ::= { adClusterAppEntry 4 }
        
    adClusterAppSyncState       OBJECT-TYPE
        SYNTAX                  INTEGER
        ACCESS                  read-only
        STATUS                  mandatory
        DESCRIPTION             "0--not sync 1--in sync 2--finished sync"
        ::= { adClusterAppEntry 5 }
        
    adStandByState              OBJECT-TYPE
        SYNTAX                  INTEGER
        ACCESS                  read-only
        STATUS                  mandatory
        DESCRIPTION             "0--slave 1--master"
        ::={ aD 56 }
    
    adStandBySyncState          OBJECT-TYPE
        SYNTAX                  INTEGER
        ACCESS                  read-only
        STATUS                  mandatory
        DESCRIPTION             "0--in sync 1--finished sync"
        ::= { aD 57 }
        
    adStandByLocalDevState      OBJECT-TYPE
        SYNTAX                  INTEGER
        ACCESS                  read-only
        STATUS                  mandatory
        DESCRIPTION             "0--init 1--online 2--warning 3--network failure 4--device failure 5--device silenced 6--offline"
        ::={ aD 58 }
        
    adStandByPeerDevState       OBJECT-TYPE
        SYNTAX                  INTEGER
        ACCESS                  read-only
        STATUS                  mandatory
        DESCRIPTION             "0--init 1--online 2--warning 3--network failure 4--device failure 5--device silenced 6--offline 7--none"
        ::= { aD 59 }
		
	adCpuTrapInfo	OBJECT-TYPE	
		SYNTAX			OCTET STRING
		ACCESS			read-only
		STATUS			mandatory
		DESCRIPTION		"CPU warn information, just use for cpuWarnTrap"
		::=  {  aD  60  }
    
    adMemTrapInfo	OBJECT-TYPE	
		SYNTAX			OCTET STRING
		ACCESS			read-only
		STATUS			mandatory
		DESCRIPTION		"MEM warn information, just use for memWarnTrap"
		::=  {  aD  61  }

    adDiskTrapInfo	OBJECT-TYPE	
		SYNTAX			OCTET STRING
		ACCESS			read-only
		STATUS			mandatory
		DESCRIPTION		"Disk warn information, just use for diskWarnTrap"
		::=  {  aD  62  }

    adSysConnsTrapInfo	OBJECT-TYPE	
		SYNTAX			OCTET STRING
		ACCESS			read-only
		STATUS			mandatory
		DESCRIPTION		"SYS connections warn information, just use for sysConnsWarnTrap"
		::=  {  aD  63  }

    adVsConnsTrapInfo	OBJECT-TYPE	
		SYNTAX			OCTET STRING
		ACCESS			read-only
		STATUS			mandatory
		DESCRIPTION		"VS connections warn information, just use for vsConnsWarnTrap"
		::=  {  aD  64  }
	
    adVsStatusTrapInfo	OBJECT-TYPE	
		SYNTAX			OCTET STRING
		ACCESS			read-only
		STATUS			mandatory
		DESCRIPTION		"VS status warn information, just use for vsStatusWarnTrap"
		::=  {  aD  65  }
    
    adNodeStatusTrapInfo	OBJECT-TYPE	
		SYNTAX			OCTET STRING
		ACCESS			read-only
		STATUS			mandatory
		DESCRIPTION		"Node status warn information, just use for nodeStatusWarnTrap"
		::=  {  aD  66  }
	
    adLinkStatusTrapInfo	OBJECT-TYPE	
		SYNTAX			OCTET STRING
		ACCESS			read-only
		STATUS			mandatory
		DESCRIPTION		"Link status warn information, just use for linkStatusWarnTrap"
		::=  {  aD  67  }
    
    adCrlTrapInfo	OBJECT-TYPE	
		SYNTAX			OCTET STRING
		ACCESS			read-only
		STATUS			mandatory
		DESCRIPTION		"Crl status warn information, just use for crlWarnTrap"
		::=  {  aD  68  }
    
    adAttackTrapInfo	OBJECT-TYPE	
		SYNTAX			OCTET STRING
		ACCESS			read-only
		STATUS			mandatory
		DESCRIPTION		"Attack warn information, just use for attackWarnTrap"
		::=  {  aD  69  }
        
    adClusterTrapInfo	OBJECT-TYPE	
		SYNTAX			OCTET STRING
		ACCESS			read-only
		STATUS			mandatory
		DESCRIPTION		"Cluster warn information, just use for clusterWarnTrap"
		::=  {  aD  70  }

    adLogRegexTrapInfo	OBJECT-TYPE	
		SYNTAX			OCTET STRING
		ACCESS			read-only
		STATUS			mandatory
		DESCRIPTION		"Cluster warn information, just use for logRegexWarnTrap"
		::=  {  aD  71  }
	
    adCrlLoadTrapInfo	OBJECT-TYPE	
		SYNTAX			OCTET STRING
		ACCESS			read-only
		STATUS			mandatory
		DESCRIPTION		"VS conns trap info"
		::=  {  aD  72  }

    adPowerTrapInfo  OBJECT-TYPE	
		SYNTAX			OCTET STRING
		ACCESS			read-only
		STATUS			mandatory
		DESCRIPTION		"Power trap info"
		::=  {  aD  73  }

    adInterfaceTrapInfo  OBJECT-TYPE	
		SYNTAX			OCTET STRING
		ACCESS			read-only
		STATUS			mandatory
		DESCRIPTION		"Link interface trap info"
		::=  {  aD  74  }

	adOffloadingNewConns	OBJECT-TYPE
		SYNTAX			Counter64
		ACCESS			read-only
		STATUS			mandatory
		DESCRIPTION		"SSL offloading new connections rate (Connection Per Second)"
		::=  {  aD  75  }
	adOffloadingSucceedConns	OBJECT-TYPE
		SYNTAX			Counter64
		ACCESS			read-only
		STATUS			mandatory
		DESCRIPTION		"SSL offloading succeed connections (Connection)"
		::=  {  aD  76  }
	adOffloadingSucceedNewConns	OBJECT-TYPE
		SYNTAX			Counter64
		ACCESS			read-only
		STATUS			mandatory
		DESCRIPTION		"SSL offloading succeed new connections rate (Connection Per Second)"
		::=  {  aD  77  }
	adOffloadingConns	OBJECT-TYPE
		SYNTAX			Counter64
		ACCESS			read-only
		STATUS			mandatory
		DESCRIPTION		"SSL offloading connections (Connection)"
		::=  {  aD  78  }
	adVsConnsEst	OBJECT-TYPE	
		SYNTAX			INTEGER
		ACCESS			read-only
		STATUS			mandatory
		DESCRIPTION		"virtual service connections_est"
		::=  {  aD  79  }
	adPoolNewConns	OBJECT-TYPE	
		SYNTAX			INTEGER
		ACCESS			read-only
		STATUS			mandatory
		DESCRIPTION		"new pool connections"
		::=  {  aD  80  }
	adPoolConns	OBJECT-TYPE	
		SYNTAX			INTEGER
		ACCESS			read-only
		STATUS			mandatory
		DESCRIPTION		"pool connections"
		::=  {  aD  81  }
	adPoolConnsEst	OBJECT-TYPE	
		SYNTAX			INTEGER
		ACCESS			read-only
		STATUS			mandatory
		DESCRIPTION		"pool connections_est"
		::=  {  aD  82  }
	adPoolHttpRequest	OBJECT-TYPE	
		SYNTAX			INTEGER
		ACCESS			read-only
		STATUS			mandatory
		DESCRIPTION		"pool http request"
		::=  {  aD  83  }		
	adVsnewConnsTrapInfo	OBJECT-TYPE	
		SYNTAX			OCTET STRING
		ACCESS			read-only
		STATUS			mandatory
		DESCRIPTION		"virtual service new connections warn information,just use for vsnewConnsWarnTrap"
		::=  {  aD  84  }
		
	adSysnewConnsTrapInfo	OBJECT-TYPE	
		SYNTAX			OCTET STRING
		ACCESS			read-only
		STATUS			mandatory
		DESCRIPTION		"system new connections warn information,just use for sysnewConnsWarnTrap"
		::=  {  aD  85  }
		
	adWanFluxTrapInfo	OBJECT-TYPE	
		SYNTAX			OCTET STRING
		ACCESS			read-only
		STATUS			mandatory
		DESCRIPTION		"Wan throughput warn information,just use for wanFluxWarnTrap"
		::=  {  aD  86  }
	throughput	OBJECT-TYPE
		SYNTAX			INTEGER
		ACCESS			read-only
		STATUS			mandatory
		DESCRIPTION		"all wan links' network throughput"
		::=  {  aD  87  }
	adHostTable	OBJECT-TYPE
		SYNTAX		SEQUENCE  OF  AdHostEntry
		ACCESS		not-accessible
		STATUS		mandatory
		DESCRIPTION	"AD host infomation"
		::=  { aD  88 }

	AdHostEntry	OBJECT-TYPE
		SYNTAX		AdHostEntry
		ACCESS		not-accessible
		STATUS		mandatory
		DESCRIPTION	"One host infomation"
		INDEX		{  hostIndex  }
		::=  { adHostTable 1 }

	AdHostEntry  ::=  SEQUENCE {
		hostIndex  INTEGER,
		adHostName  OCTET STRING,
		adHostBitIn  Counter64,
		adHostBitOut  Counter64,
		adHostBitTotal  Counter64,
		adHostConn  Counter64,
		adHostConnEst  Counter64,
		adHostConnRate  Counter64,
		adHostRequestRate  Counter64
		}

	hostIndex	OBJECT-TYPE	
		SYNTAX			INTEGER
		ACCESS			not-accessible
		STATUS			mandatory
		DESCRIPTION		"The host index"
		::=  {  AdHostEntry  1  }


	adHostName	OBJECT-TYPE	
		SYNTAX			OCTET STRING
		ACCESS			read-only
		STATUS			mandatory
		DESCRIPTION		"Name of host"
		::=  {  AdHostEntry  2  }

	adHostBitIn	OBJECT-TYPE	
		SYNTAX			Counter64
		ACCESS			read-only
		STATUS			mandatory
		DESCRIPTION		"In bits of host (Bit)"
		::=  {  AdHostEntry  3  }

	adHostBitOut	OBJECT-TYPE	
		SYNTAX			Counter64
		ACCESS			read-only
		STATUS			mandatory
		DESCRIPTION		"Out bits of host (Bit)"
		::=  {  AdHostEntry  4  }

	adHostBitTotal	OBJECT-TYPE	
		SYNTAX			Counter64
		ACCESS			read-only
		STATUS			mandatory
		DESCRIPTION		"Total bits of host (Bit)"
		::=  {  AdHostEntry  5  }

	adHostConn	OBJECT-TYPE	
		SYNTAX			Counter64
		ACCESS			read-only
		STATUS			mandatory
		DESCRIPTION		"Concurrent connection of host (Connection)"
		::=  {  AdHostEntry  6  }

	adHostConnEst	OBJECT-TYPE	
		SYNTAX			Counter64
		ACCESS			read-only
		STATUS			mandatory
		DESCRIPTION		"Concurrent connection(established) of host (Connection)"
		::=  {  AdHostEntry  7  }
		
	adHostConnRate	OBJECT-TYPE	
		SYNTAX			Counter64
		ACCESS			read-only
		STATUS			mandatory
		DESCRIPTION		"New connection rate of host (Connection Per Second)"
		::=  {  AdHostEntry  8  }

	adHostRequestRate	OBJECT-TYPE	
		SYNTAX			Counter64
		ACCESS			read-only
		STATUS			mandatory
		DESCRIPTION		"Request rate of host (Request Per Second)"
		::=  {  AdHostEntry  9  }

	adAcceleratorTable	OBJECT-TYPE
		SYNTAX		SEQUENCE  OF  AdAcceleratorEntry
		ACCESS		not-accessible
		STATUS		mandatory
		DESCRIPTION	"AD Accelerator infomation"
		::=  { aD  90 }

	adAcceleratorEntry	OBJECT-TYPE
		SYNTAX		AdAcceleratorEntry
		ACCESS		not-accessible
		STATUS		mandatory
		DESCRIPTION	"One accelerator infomation"
		INDEX		{  acceleratorIndex  }
		::=  { adAcceleratorTable 1 }

	AdAcceleratorEntry  ::=  SEQUENCE {
		acceleratorIndex        INTEGER,
		adAcceleratorStatus     INTEGER
		}

	acceleratorIndex	OBJECT-TYPE
		SYNTAX			INTEGER
		ACCESS			not-accessible
		STATUS			mandatory
		DESCRIPTION		"The accelerator index"
		::=  {  adAcceleratorEntry  1  }

	adAcceleratorStatus	OBJECT-TYPE
		SYNTAX			INTEGER
		ACCESS			read-only
		STATUS			mandatory
		DESCRIPTION		"The accelerator status: [0:normal, 1:not exist, 2:init err, 3:crypto err]"
		::=  {  adAcceleratorEntry  2  }

	adCryptoDevTable	OBJECT-TYPE
		SYNTAX		SEQUENCE  OF  AdCryptoDevEntry
		ACCESS		not-accessible
		STATUS		mandatory
		DESCRIPTION	"AD CryptoDev infomation"
		::=  { aD  91 }

	adCryptoDevEntry	OBJECT-TYPE
		SYNTAX		AdCryptoDevEntry
		ACCESS		not-accessible
		STATUS		mandatory
		DESCRIPTION	"One CryptoDev infomation"
		INDEX		{  cryptoDevIndex  }
		::=  { adCryptoDevTable 1 }

	AdCryptoDevEntry  ::=  SEQUENCE {
		cryptoDevIndex        INTEGER,
		adCryptoDevStatus     INTEGER
		}

	cryptoDevIndex	OBJECT-TYPE
		SYNTAX			INTEGER
		ACCESS			not-accessible
		STATUS			mandatory
		DESCRIPTION		"The CryptoDev index"
		::=  {  adCryptoDevEntry  1  }

	adCryptoDevStatus	OBJECT-TYPE
		SYNTAX			INTEGER
		ACCESS			read-only
		STATUS			mandatory
		DESCRIPTION		"The CryptoDev status: [0:normal, 1:not exist, 2:init err, 3:crypto err]"
		::=  {  adCryptoDevEntry  2  }

	adSerialNumber	OBJECT-TYPE
		SYNTAX			OCTET STRING
		ACCESS			read-only
		STATUS			mandatory
		DESCRIPTION		"The product Serial Number"
		::=  {  aD  95  }

	adCertificateTrapInfo  OBJECT-TYPE	
		SYNTAX			OCTET STRING
		ACCESS			read-only
		STATUS			mandatory
		DESCRIPTION		"Certificate expired trap info"
		::=  {  aD  100  }

	adDnsTcpQueryRate	OBJECT-TYPE
		SYNTAX			Counter64
		ACCESS			read-only
		STATUS			mandatory
		DESCRIPTION		"The tcp dns query speed"
		::=  {  aD  101  }

	adDnsUdpQueryRate	OBJECT-TYPE
		SYNTAX			Counter64
		ACCESS			read-only
		STATUS			mandatory
		DESCRIPTION		"The udp dns query speed"
		::=  {  aD  102  }

	adDnsRcodeNxdomain	OBJECT-TYPE
		SYNTAX			Counter64
		ACCESS			read-only
		STATUS			mandatory
		DESCRIPTION		"The number of NXDOMAIN rcode"
		::=  {  aD  103  }

	adDnsRcodeRefuse	OBJECT-TYPE
		SYNTAX			Counter64
		ACCESS			read-only
		STATUS			mandatory
		DESCRIPTION		"The number of REFUSE rcode"
		::=  {  aD  104  }

	adDnsRcodeServfail	OBJECT-TYPE
		SYNTAX			Counter64
		ACCESS			read-only
		STATUS			mandatory
		DESCRIPTION		"The number of SVRFAIL rcode"
		::=  {  aD  105  }

	adDnsRcodeDrop	OBJECT-TYPE
		SYNTAX			Counter64
		ACCESS			read-only
		STATUS			mandatory
		DESCRIPTION		"The number of DROP rcode"
		::=  {  aD  106  }

	adSecurityPoolTable	OBJECT-TYPE
		SYNTAX		SEQUENCE  OF  AdSecurityPoolEntry
		ACCESS		not-accessible
		STATUS		mandatory
		DESCRIPTION	"AD security pool infomation"
		::=  { aD  107 }

	AdSecurityPoolEntry	OBJECT-TYPE
		SYNTAX		AdSecurityPoolEntry
		ACCESS		not-accessible
		STATUS		mandatory
		DESCRIPTION	"One security pool infomation"
		INDEX		{  securityPoolIndex  }
		::=  { adSecurityPoolTable 1 }

	AdSecurityPoolEntry  ::=  SEQUENCE {
		securityPoolIndex  INTEGER,
		adSecurityPoolName  OCTET STRING,
		adSecurityPoolConfigStatus  INTEGER,
		adSecurityPoolHealthStatus  INTEGER,
		adSecurityPoolBitIn  Counter64,
		adSecurityPoolBitOut  Counter64,
		adSecurityPoolPacketIn  Counter64,
		adSecurityPoolPacketOut  Counter64,
		adSecurityPoolConnNew  Counter64,
		adSecurityPoolConnCur  Counter64,
		adSecurityPoolConnMax  Counter64,
		adSecurityPoolConnTotal  Counter64,
		adSecurityPoolRequestTotal  Counter64,
		adSecurityPoolRequestNew  Counter64,
		adSecurityPoolMysqlReadRate INTEGER,
		adSecurityPoolMysqlWriteRate INTEGER,
		adSecurityPoolConnCurEst  Counter64
		}

	securityPoolIndex	OBJECT-TYPE
		SYNTAX			INTEGER
		ACCESS			not-accessible
		STATUS			mandatory
		DESCRIPTION		"The security pool index"
		::=  {  AdSecurityPoolEntry  1  }


	adSecurityPoolName	OBJECT-TYPE
		SYNTAX			OCTET STRING
		ACCESS			read-only
		STATUS			mandatory
		DESCRIPTION		"Name of security pool"
		::=  {  AdSecurityPoolEntry  2  }


	adSecurityPoolConfigStatus	OBJECT-TYPE
		SYNTAX			INTEGER
		ACCESS			read-only
		STATUS			mandatory
		DESCRIPTION		"Config status of security pool: [0:disable, 1:enable]"
		::=  {  AdSecurityPoolEntry  3  }

	adSecurityPoolHealthStatus	OBJECT-TYPE
		SYNTAX			INTEGER
		ACCESS			read-only
		STATUS			mandatory
		DESCRIPTION		"Health status of security pool: [0:failure, 1:normal, 2:busy, 3:alert]"
		::=  {  AdSecurityPoolEntry  4  }


	adSecurityPoolBitIn	OBJECT-TYPE
		SYNTAX			Counter64
		ACCESS			read-only
		STATUS			mandatory
		DESCRIPTION		"In bits of security pool (Bit)"
		::=  {  AdSecurityPoolEntry  5  }

	adSecurityPoolBitOut	OBJECT-TYPE
		SYNTAX			Counter64
		ACCESS			read-only
		STATUS			mandatory
		DESCRIPTION		"Out bits of security pool (Bit)"
		::=  {  AdSecurityPoolEntry  6  }

	adSecurityPoolPacketIn	OBJECT-TYPE
		SYNTAX			Counter64
		ACCESS			read-only
		STATUS			mandatory
		DESCRIPTION		"In packets of security pool (Packet)"
		::=  {  AdSecurityPoolEntry  7  }

	adSecurityPoolPacketOut	OBJECT-TYPE
		SYNTAX			Counter64
		ACCESS			read-only
		STATUS			mandatory
		DESCRIPTION		"Out packets of security pool (Packet)"
		::=  {  AdSecurityPoolEntry  8  }

	adSecurityPoolConnNew	OBJECT-TYPE
		SYNTAX			Counter64
		ACCESS			read-only
		STATUS			mandatory
		DESCRIPTION		"New connection of security pool (Connection Per Second)"
		::=  {  AdSecurityPoolEntry  9  }

	adSecurityPoolConnCur	OBJECT-TYPE
		SYNTAX			Counter64
		ACCESS			read-only
		STATUS			mandatory
		DESCRIPTION		"Current connection of security pool (Connection)"
		::=  {  AdSecurityPoolEntry  10  }

	adSecurityPoolConnMax	OBJECT-TYPE
		SYNTAX			Counter64
		ACCESS			read-only
		STATUS			mandatory
		DESCRIPTION		"Max connection of security pool (Connection)"
		::=  {  AdSecurityPoolEntry  11  }

	adSecurityPoolConnTotal	OBJECT-TYPE
		SYNTAX			Counter64
		ACCESS			read-only
		STATUS			mandatory
		DESCRIPTION		"Total connection of security pool (Connection)"
		::=  {  AdSecurityPoolEntry  12  }

	adSecurityPoolRequestTotal	OBJECT-TYPE
		SYNTAX			Counter64
		ACCESS			read-only
		STATUS			mandatory
		DESCRIPTION		"Total requests of security pool (Request)"
		::=  {  AdSecurityPoolEntry  13  }

	adSecurityPoolRequestNew	OBJECT-TYPE
		SYNTAX			Counter64
		ACCESS			read-only
		STATUS			mandatory
		DESCRIPTION		"Requests of security pool (Request Per Second)"
		::=  {  AdSecurityPoolEntry  14  }

	adSecurityPoolMysqlReadRate	OBJECT-TYPE
		SYNTAX			INTEGER
		ACCESS			read-only
		STATUS			mandatory
		DESCRIPTION		"MySQL read rate"
		::=  {  AdSecurityPoolEntry  15  }

	adSecurityPoolMysqlWriteRate	OBJECT-TYPE
		SYNTAX			INTEGER
		ACCESS			read-only
		STATUS			mandatory
		DESCRIPTION		"MySQL write rate"
		::=  {  AdSecurityPoolEntry  16  }

	adSecurityPoolConnCurEst	OBJECT-TYPE
		SYNTAX			Counter64
		ACCESS			read-only
		STATUS			mandatory
		DESCRIPTION		"current connection_est of security pool"
		::=  {  AdSecurityPoolEntry  17  }

	adSecurityNodeTable	OBJECT-TYPE
		SYNTAX		SEQUENCE  OF  AdSecurityNodeEntry
		ACCESS		not-accessible
		STATUS		mandatory
		DESCRIPTION	"AD Security Node infomation"
		::=  { aD  108 }

	AdSecurityNodeEntry	OBJECT-TYPE
		SYNTAX		AdSecurityNodeEntry
		ACCESS		not-accessible
		STATUS		mandatory
		DESCRIPTION	"One Security Node infomation"
		INDEX		{  securityNodeIndex  }
		::=  { adSecurityNodeTable 1 }

	AdSecurityNodeEntry  ::=  SEQUENCE {
		securityNodeIndex  INTEGER,
		adSecurityNodeName  OCTET STRING,
		adSecurityNodeConfigStatus  INTEGER,
		adSecurityNodeHealthStatus  INTEGER,
		adSecurityNodeBitIn  Counter64,
		adSecurityNodeBitOut  Counter64,
		adSecurityNodePacketIn  Counter64,
		adSecurityNodePacketOut  Counter64,
		adSecurityNodeConnNew  Counter64,
		adSecurityNodeConnCur  Counter64,
		adSecurityNodeConnMax  Counter64,
		adSecurityNodeConnTotal  Counter64,
		adSecurityNodeRequestTotal  Counter64,
		adSecurityNodeRequestNew  Counter64,
		adSecurityNodePoolName   OCTET STRING,
		adSecurityNodeMysqlReadRate INTEGER,
		adSecurityNodeMysqlWriteRate INTEGER,
		adSecurityNodeIP  OCTET STRING,
		adSecurityNodePort  INTEGER,
		adSecurityNodeConnCurEst  Counter64
		}

	securityNodeIndex	OBJECT-TYPE
		SYNTAX			INTEGER
		ACCESS			not-accessible
		STATUS			mandatory
		DESCRIPTION		"The security node index"
		::=  {  AdSecurityNodeEntry  1  }


	adSecurityNodeName	OBJECT-TYPE
		SYNTAX			OCTET STRING
		ACCESS			read-only
		STATUS			mandatory
		DESCRIPTION		"Name of Security node"
		::=  {  AdSecurityNodeEntry  2  }


	adSecurityNodeConfigStatus	OBJECT-TYPE
		SYNTAX			INTEGER
		ACCESS			read-only
		STATUS			mandatory
		DESCRIPTION		"Config status of Security node: [0:disable, 1:enable, 2:offline]"
		::=  {  AdSecurityNodeEntry  3  }


	adSecurityNodeHealthStatus	OBJECT-TYPE
		SYNTAX			INTEGER
		ACCESS			read-only
		STATUS			mandatory
		DESCRIPTION		"Health status of Security node: [0:failure, 1:normal, 2:busy]"
		::=  {  AdSecurityNodeEntry  4  }

	adSecurityNodeBitIn	OBJECT-TYPE
		SYNTAX			Counter64
		ACCESS			read-only
		STATUS			mandatory
		DESCRIPTION		"In bits of Security node (Bit)"
		::=  {  AdSecurityNodeEntry  5  }

	adSecurityNodeBitOut	OBJECT-TYPE
		SYNTAX			Counter64
		ACCESS			read-only
		STATUS			mandatory
		DESCRIPTION		"Out bits of Security node (Bit)"
		::=  {  AdSecurityNodeEntry  6  }

	adSecurityNodePacketIn	OBJECT-TYPE
		SYNTAX			Counter64
		ACCESS			read-only
		STATUS			mandatory
		DESCRIPTION		"In packets of Security node (Packet)"
		::=  {  AdSecurityNodeEntry  7  }

	adSecurityNodePacketOut	OBJECT-TYPE
		SYNTAX			Counter64
		ACCESS			read-only
		STATUS			mandatory
		DESCRIPTION		"Out packets of Security node ({Packet})"
		::=  {  AdSecurityNodeEntry  8  }

	adSecurityNodeConnNew	OBJECT-TYPE
		SYNTAX			Counter64
		ACCESS			read-only
		STATUS			mandatory
		DESCRIPTION		"New connection of Security node (Request Per Second)"
		::=  {  AdSecurityNodeEntry  9  }

	adSecurityNodeConnCur	OBJECT-TYPE
		SYNTAX			Counter64
		ACCESS			read-only
		STATUS			mandatory
		DESCRIPTION		"Current connection of Security node (Connection)"
		::=  {  AdSecurityNodeEntry  10  }

	adSecurityNodeConnMax	OBJECT-TYPE
		SYNTAX			Counter64
		ACCESS			read-only
		STATUS			mandatory
		DESCRIPTION		"Max connection of Security node (Connection)"
		::=  {  AdSecurityNodeEntry  11  }

	adSecurityNodeConnTotal	OBJECT-TYPE
		SYNTAX			Counter64
		ACCESS			read-only
		STATUS			mandatory
		DESCRIPTION		"Total connection of Security node (Connection)"
		::=  {  AdSecurityNodeEntry  12  }

	adSecurityNodeRequestTotal	OBJECT-TYPE
		SYNTAX			Counter64
		ACCESS			read-only
		STATUS			mandatory
		DESCRIPTION		"Total requests of Security node (Request)"
		::=  {  AdSecurityNodeEntry  13  }

	adSecurityNodeRequestNew	OBJECT-TYPE
		SYNTAX			Counter64
		ACCESS			read-only
		STATUS			mandatory
		DESCRIPTION		"Requests rate of Security node (Request Per Second)"
		::=  {  AdSecurityNodeEntry  14  }

    adSecurityNodePoolName	OBJECT-TYPE
		SYNTAX			OCTET STRING
		ACCESS			read-only
		STATUS			mandatory
		DESCRIPTION		"Pool name of Security node"
		::=  {  AdSecurityNodeEntry  15  }

    adSecurityNodeMysqlReadRate     OBJECT-TYPE
		SYNTAX			INTEGER
		ACCESS			read-only
		STATUS			mandatory
		DESCRIPTION		"Mysql read rate"
		::=  {  AdSecurityNodeEntry  16  }

	adSecurityNodeMysqlWriteRate     OBJECT-TYPE
		SYNTAX			INTEGER
		ACCESS			read-only
		STATUS			mandatory
		DESCRIPTION		"Mysql write rate"
		::=  {  AdSecurityNodeEntry  17  }

	adSecurityNodeIP	OBJECT-TYPE
		SYNTAX			OCTET STRING
		ACCESS			read-only
		STATUS			mandatory
		DESCRIPTION		"IP of Security node"
		::=  {  AdSecurityNodeEntry  18  }

	adSecurityNodePort	OBJECT-TYPE
		SYNTAX			INTEGER
		ACCESS			read-only
		STATUS			mandatory
		DESCRIPTION		"Port of Security node"
		::=  {  AdSecurityNodeEntry  19  }

	adSecurityNodeConnCurEst	OBJECT-TYPE
		SYNTAX			Counter64
		ACCESS			read-only
		STATUS			mandatory
		DESCRIPTION		"current connection_est of Security node"
		::=  {  AdSecurityNodeEntry  20  }

	adSecurityStatusTrapInfo  OBJECT-TYPE
		SYNTAX			OCTET STRING
		ACCESS			read-only
		STATUS			mandatory
		DESCRIPTION		"Security expired trap info"
		::=  {  aD  109  }
END
